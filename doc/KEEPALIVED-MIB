-- ----------------------------------------------------------------------
-- MIB file for keepalived (http://www.keepalived.org)
-- ----------------------------------------------------------------------
--
-- There are two sections in this MIB: vrrp and check.

KEEPALIVED-MIB DEFINITIONS ::= BEGIN

IMPORTS
    OBJECT-TYPE, MODULE-IDENTITY,
    Integer32, Unsigned32, Counter32, Counter64,
    Gauge32, enterprises, NOTIFICATION-TYPE
        FROM SNMPv2-SMI
    OBJECT-GROUP, MODULE-COMPLIANCE, NOTIFICATION-GROUP
        FROM SNMPv2-CONF
    InetAddressType, InetAddress, InetPortNumber,
    InetAddressPrefixLength, InetScopeType
        FROM INET-ADDRESS-MIB
    InterfaceIndex, ifIndex
        FROM IF-MIB
    DisplayString, TEXTUAL-CONVENTION, TruthValue
        FROM SNMPv2-TC;

keepalived MODULE-IDENTITY
     LAST-UPDATED "201608231200Z"
     ORGANIZATION "Keepalived"
     CONTACT-INFO "http://www.keepalived.org"
     DESCRIPTION
        "This MIB describes objects used by keepalived, both
         for VRRP and health checker."
     REVISION "201608231200Z"
     DESCRIPTION "dbus support added"
     REVISION "201608230000Z"
     DESCRIPTION "add IPv6 persistence granularity"
     REVISION "201608030000Z"
     DESCRIPTION "net-namespace added"
     REVISION "201607260000Z"
     DESCRIPTION "64-bit stats added"
     REVISION "201607100000Z"
     DESCRIPTION "enhanced virtual rules and routes"
     REVISION "201607030000Z"
     DESCRIPTION "change vrrpRuleIndex to unsigned"
     REVISION "201607021200Z"
     DESCRIPTION "add lvs timeout parameters"
     REVISION "201607020000Z"
     DESCRIPTION
	"added LVS sync daemon parameters and deprecated
	 LVS sync daemon objects within VRRP instance"
     REVISION "201606290000Z"
     DESCRIPTION "add lvs_flush"
     REVISION "201606030000Z"
     DESCRIPTION "update comment for vrrpInstancePreemptDelay"
     REVISION "201605221540Z"
     DESCRIPTION "smtpServerPort added"
     REVISION "201510270000Z"
     DESCRIPTION "routerId added to traps variables"
     REVISION "200904080000Z"
     DESCRIPTION "Initial revision"

     ::= { project 5 }

-- We are hosted under Debian OID. See http://dsa.debian.org/iana/
debian          OBJECT IDENTIFIER ::= { enterprises 9586 }
project         OBJECT IDENTIFIER ::= { debian 100 }

VrrpState ::= TEXTUAL-CONVENTION
    STATUS       current
    DESCRIPTION
    "Represents a VRRP state."
    SYNTAX INTEGER {
        init(0),
    backup(1),
    master(2),
    fault(3),
    unknown(4)
    }

RouteType ::= TEXTUAL-CONVENTION
    STATUS	current
    DESCRIPTION
	"Type of route"
    SYNTAX	INTEGER { unicast(1),
			  ecmp(2),
		          blackhole(3),
		          anycast(4),
		          multicast(5),
		          broadcast(6),
		          unreachable(7),
		          prohibit(8),
			  throw(9),
		          nat(10),
		          xresolve(11) }

RuleAction ::= TEXTUAL-CONVENTION
    STATUS	current
    DESCRIPTION
	"Action of rule"
    SYNTAX	INTEGER { table(1),
			  goto(2),
			  nop(3),
		          blackhole(6),
		          unreachable(7),
		          prohibit(8) }

Realm ::= TEXTUAL-CONVENTION
    DISPLAY-HINT "d"
    STATUS	current
    DESCRIPTION
	"Route realm."
    SYNTAX	Unsigned32 (1..65535)

PrefType ::= TEXTUAL-CONVENTION
    STATUS	current
    DESCRIPTION
	"Preference type of route"
    SYNTAX	INTEGER { low(1), medium(2), high(3) }

EncapType ::= TEXTUAL-CONVENTION
    STATUS	current
    DESCRIPTION
	"Encapsulation type of route"
    SYNTAX INTEGER { mpls(1), ip(2), ila(3), ip6(4) }

global          OBJECT IDENTIFIER ::= { keepalived 1 }
vrrp            OBJECT IDENTIFIER ::= { keepalived 2 }
check           OBJECT IDENTIFIER ::= { keepalived 3 }
conformance     OBJECT IDENTIFIER ::= { keepalived 4 }

-- ----------------------------------------------------------------------
-- Global part
-- ----------------------------------------------------------------------

version OBJECT-TYPE
    SYNTAX DisplayString
    MAX-ACCESS read-only
    STATUS current
    DESCRIPTION
        "Version of keepalived"
    ::= { global 1 }

routerId OBJECT-TYPE
    SYNTAX DisplayString
    MAX-ACCESS read-only
    STATUS current
    DESCRIPTION
        "Router ID"
    ::= { global 2 }

mail    OBJECT IDENTIFIER ::= { global 3 }

smtpServerAddressType OBJECT-TYPE
    SYNTAX InetAddressType
    MAX-ACCESS read-only
    STATUS current
    DESCRIPTION
        "Address type for SMTP server."
    ::= { mail 1 }

smtpServerAddress OBJECT-TYPE
    SYNTAX InetAddress
    MAX-ACCESS read-only
    STATUS current
    DESCRIPTION
        "Address of SMTP server."
    ::= { mail 2 }

smtpServerTimeout OBJECT-TYPE
    SYNTAX Unsigned32
    UNITS "seconds"
    MAX-ACCESS read-only
    STATUS current
    DESCRIPTION
        "SMTP server connection timeout."
    ::= { mail 3 }

emailFrom OBJECT-TYPE
    SYNTAX DisplayString
    MAX-ACCESS read-only
    STATUS current
    DESCRIPTION
        "Email address for the From field."
    ::= { mail 4 }

emailTable OBJECT-TYPE
    SYNTAX SEQUENCE OF EmailEntry
    MAX-ACCESS not-accessible
    STATUS current
    DESCRIPTION
        "Table of email notification addresses."
    ::= { mail 5 }

smtpServerPort OBJECT-TYPE
    SYNTAX InetPortNumber
    MAX-ACCESS read-only
    STATUS current
    DESCRIPTION
        "Port of SMTP server."
    ::= { mail 6 }

emailEntry OBJECT-TYPE
    SYNTAX EmailEntry
    MAX-ACCESS not-accessible
    STATUS current
    DESCRIPTION
        "Email address to be notified with an alert."
    INDEX { emailIndex }
    ::= { emailTable 1 }

EmailEntry ::= SEQUENCE {
    emailIndex Integer32,
    emailAddress DisplayString
}

emailIndex OBJECT-TYPE
    SYNTAX Integer32 (1..2147483647)
    MAX-ACCESS not-accessible
    STATUS current
    DESCRIPTION
        "Index for the email address."
    ::= { emailEntry 1 }

emailAddress OBJECT-TYPE
    SYNTAX DisplayString
    MAX-ACCESS read-only
    STATUS current
    DESCRIPTION
        "Email address to be notified when an alert is raised."
    ::= { emailEntry 2 }

trapEnable OBJECT-TYPE
    SYNTAX INTEGER { enabled(1), disabled(2) }
    MAX-ACCESS read-only
    STATUS current
    DESCRIPTION
        "Indicate whether traps should be sent for various events."
    ::= { global 4 }

linkBeat OBJECT-TYPE
    SYNTAX INTEGER { netlink(1), polling(2) }
    MAX-ACCESS read-only
    STATUS current
    DESCRIPTION
        "Indicate which method is used to check if a link is up or
        down. netlink(1) means that the kernel will push a link state
        change while polling(2) means that the status of the link is
        checked periodically."
    ::= { global 5 }

lvsFlush OBJECT-TYPE
    SYNTAX INTEGER { enabled(1), disabled(2) }
    MAX-ACCESS read-only
    STATUS current
    DESCRIPTION
        "Indicate whether LVS config is flushed at startup."
    ::= { global 6 }

ipvs64BitStats OBJECT-TYPE
    SYNTAX TruthValue
    MAX-ACCESS read-only
    STATUS current
    DESCRIPTION
        "True if 64-bit stats counters are available for ipvs, false otherwise."
    ::= { global 7 }

netNamespace OBJECT-TYPE
    SYNTAX DisplayString
    MAX-ACCESS read-only
    STATUS current
    DESCRIPTION
        "The name of the net namespace keepalived is running in."
    ::= { global 8 }

dbus OBJECT-TYPE
    SYNTAX TruthValue
    MAX-ACCESS read-only
    STATUS current
    DESCRIPTION
        "True if the DBus interface is enabled."
    ::= { global 9 }

-- ----------------------------------------------------------------------
-- VRRP part
-- ----------------------------------------------------------------------

-- Sync groups
-- see vrrp.h

vrrpSyncGroupTable OBJECT-TYPE
    SYNTAX SEQUENCE OF VrrpSyncGroupEntry
    MAX-ACCESS not-accessible
    STATUS current
    DESCRIPTION
        "Table of sync groups"
    ::= { vrrp 1 }

vrrpSyncGroupEntry OBJECT-TYPE
    SYNTAX VrrpSyncGroupEntry
    MAX-ACCESS not-accessible
    STATUS current
    DESCRIPTION
        "Information describing a sync group"
    INDEX { vrrpSyncGroupIndex }
    ::= { vrrpSyncGroupTable 1 }

VrrpSyncGroupEntry ::= SEQUENCE {
    vrrpSyncGroupIndex Integer32,
    vrrpSyncGroupName DisplayString,
    vrrpSyncGroupState VrrpState,
    vrrpSyncGroupSmtpAlert INTEGER,
    vrrpSyncGroupNotifyExec INTEGER,
    vrrpSyncGroupScriptMaster DisplayString,
    vrrpSyncGroupScriptBackup DisplayString,
    vrrpSyncGroupScriptFault DisplayString,
    vrrpSyncGroupScript DisplayString
}

vrrpSyncGroupIndex OBJECT-TYPE
    SYNTAX Integer32 (1..2147483647)
    MAX-ACCESS not-accessible
    STATUS current
    DESCRIPTION
        "Index of the synchronisation group."
    ::= { vrrpSyncGroupEntry 1 }

vrrpSyncGroupName OBJECT-TYPE
    SYNTAX DisplayString
    MAX-ACCESS read-only
    STATUS current
    DESCRIPTION
        "Name of the synchronisation group."
    ::= {vrrpSyncGroupEntry 2 }

vrrpSyncGroupState OBJECT-TYPE
    SYNTAX VrrpState
    MAX-ACCESS read-only
    STATUS current
    DESCRIPTION
        "Current state of the synchronisation group."
    ::= {vrrpSyncGroupEntry 3 }

vrrpSyncGroupSmtpAlert OBJECT-TYPE
    SYNTAX INTEGER { enabled(1), disabled(2) }
    MAX-ACCESS read-only
    STATUS current
    DESCRIPTION
        "Will SMTP alert be sent for this synchronisation group?"
    ::= {vrrpSyncGroupEntry 4 }

vrrpSyncGroupNotifyExec OBJECT-TYPE
    SYNTAX INTEGER { enabled(1), disabled(2) }
    MAX-ACCESS read-only
    STATUS current
    DESCRIPTION
        "Will we execute notification script for this group?"
    ::= {vrrpSyncGroupEntry 5 }

vrrpSyncGroupScriptMaster OBJECT-TYPE
    SYNTAX DisplayString
    MAX-ACCESS read-only
    STATUS current
    DESCRIPTION
        "Script to execute when the group becomes master."
    ::= {vrrpSyncGroupEntry 6 }

vrrpSyncGroupScriptBackup OBJECT-TYPE
    SYNTAX DisplayString
    MAX-ACCESS read-only
    STATUS current
    DESCRIPTION
        "Script to execute when the group becomes backup."
    ::= {vrrpSyncGroupEntry 7 }

vrrpSyncGroupScriptFault OBJECT-TYPE
    SYNTAX DisplayString
    MAX-ACCESS read-only
    STATUS current
    DESCRIPTION
        "Script to execute when the group is in fault state."
    ::= {vrrpSyncGroupEntry 8 }

vrrpSyncGroupScript OBJECT-TYPE
    SYNTAX DisplayString
    MAX-ACCESS read-only
    STATUS current
    DESCRIPTION
        "Script to execute whenever a state change occurs."
    ::= {vrrpSyncGroupEntry 9 }

vrrpSyncGroupMemberTable OBJECT-TYPE
    SYNTAX SEQUENCE OF VrrpSyncGroupMemberEntry
    MAX-ACCESS not-accessible
    STATUS current
    DESCRIPTION
        "Table of instances contained in sync groups"
    ::= { vrrp 2 }

vrrpSyncGroupMemberEntry OBJECT-TYPE
    SYNTAX VrrpSyncGroupMemberEntry
    MAX-ACCESS not-accessible
    STATUS current
    DESCRIPTION
        "Information describing a member of a sync group"
    INDEX { vrrpSyncGroupIndex, vrrpSyncGroupMemberInstanceIndex }
    ::= { vrrpSyncGroupMemberTable 1 }

VrrpSyncGroupMemberEntry ::= SEQUENCE {
    vrrpSyncGroupMemberInstanceIndex Integer32,
    vrrpSyncGroupMemberName DisplayString
}

vrrpSyncGroupMemberInstanceIndex OBJECT-TYPE
    SYNTAX Integer32 (1..2147483647)
    MAX-ACCESS not-accessible
    STATUS current
    DESCRIPTION
        "Index of an instance in a synchronisation group.
         There is no relation with this index and the index of the
         corresponding instance in vrrpInstanceTable. Use the name
         to find out the corresponding instance."
    ::= { vrrpSyncGroupMemberEntry 1 }

vrrpSyncGroupMemberName OBJECT-TYPE
    SYNTAX DisplayString
    MAX-ACCESS read-only
    STATUS current
    DESCRIPTION
        "Name of the instance contained in the synchronisation group."
    ::= { vrrpSyncGroupMemberEntry 2 }

-- VRRP instances
-- see vrrp.h

vrrpInstanceTable OBJECT-TYPE
    SYNTAX SEQUENCE OF VrrpInstanceEntry
    MAX-ACCESS not-accessible
    STATUS current
    DESCRIPTION
        "Table of VRRP instances"
    ::= { vrrp 3 }

vrrpInstanceEntry OBJECT-TYPE
    SYNTAX VrrpInstanceEntry
    MAX-ACCESS not-accessible
    STATUS current
    DESCRIPTION
        "Information describing a sync group"
    INDEX { vrrpInstanceIndex }
    ::= { vrrpInstanceTable 1 }

VrrpInstanceEntry ::= SEQUENCE {
    vrrpInstanceIndex INTEGER,
    vrrpInstanceName DisplayString,
    vrrpInstanceVirtualRouterId Unsigned32,
    vrrpInstanceState VrrpState,
    vrrpInstanceInitialState VrrpState,
    vrrpInstanceWantedState VrrpState,
    vrrpInstanceBasePriority Integer32,
    vrrpInstanceEffectivePriority Integer32,
    vrrpInstanceVipsStatus INTEGER,
    vrrpInstancePrimaryInterface DisplayString,
    vrrpInstanceTrackPrimaryIf INTEGER,
    vrrpInstanceAdvertisementsInt Unsigned32,
    vrrpInstancePreempt INTEGER,
    vrrpInstancePreemptDelay Unsigned32,
    vrrpInstanceAuthType INTEGER,
    vrrpInstanceLvsSyncDaemon INTEGER,
    vrrpInstanceLvsSyncInterface DisplayString,
    vrrpInstanceSyncGroup DisplayString,
    vrrpInstanceGarpDelay Unsigned32,
    vrrpInstanceSmtpAlert INTEGER,
    vrrpInstanceNotifyExec INTEGER,
    vrrpInstanceScriptMaster DisplayString,
    vrrpInstanceScriptBackup DisplayString,
    vrrpInstanceScriptFault DisplayString,
    vrrpInstanceScriptStop DisplayString,
    vrrpInstanceScript DisplayString,
    vrrpInstanceAccept INTEGER
}

vrrpInstanceIndex OBJECT-TYPE
    SYNTAX INTEGER {
        static(0)
    }
    MAX-ACCESS not-accessible
    STATUS current
    DESCRIPTION
        "Index of the VRRP instance.
         Instance 0 is for static IP and static routes."
    ::= { vrrpInstanceEntry 1 }

vrrpInstanceName OBJECT-TYPE
    SYNTAX DisplayString
    MAX-ACCESS read-only
    STATUS current
    DESCRIPTION
        "Name of the VRRP instance."
    ::= { vrrpInstanceEntry 2 }

vrrpInstanceVirtualRouterId OBJECT-TYPE
    SYNTAX Unsigned32
    MAX-ACCESS read-only
    STATUS current
    DESCRIPTION
        "Virtual Router ID (VRID) for this VRRP instance."
    ::= { vrrpInstanceEntry 3 }

vrrpInstanceState OBJECT-TYPE
    SYNTAX VrrpState
    MAX-ACCESS read-only
    STATUS current
    DESCRIPTION
        "Current state of this VRRP instance."
    ::= { vrrpInstanceEntry 4 }

vrrpInstanceInitialState OBJECT-TYPE
    SYNTAX VrrpState
    MAX-ACCESS read-only
    STATUS current
    DESCRIPTION
        "Initial state of this VRRP instance."
    ::= { vrrpInstanceEntry 5 }

vrrpInstanceWantedState OBJECT-TYPE
    SYNTAX VrrpState
    MAX-ACCESS read-only
    STATUS current
    DESCRIPTION
        "State wanted by the operator for this VRRP instance."
    ::= { vrrpInstanceEntry 6 }

vrrpInstanceBasePriority OBJECT-TYPE
    SYNTAX Integer32
    MAX-ACCESS read-write
    STATUS current
    DESCRIPTION
        "Base priority (as defined in the configuration file) for this
         VRRP instance.
         This value can be modified to force the virtual router
         instance to become backup or master."
    ::= { vrrpInstanceEntry 7 }

vrrpInstanceEffectivePriority OBJECT-TYPE
    SYNTAX Integer32
    MAX-ACCESS read-only
    STATUS current
    DESCRIPTION
        "Effective priority for this VRRP instance. Status of
         interfaces and script results are used to compute this value
         from the base priority."
    ::= { vrrpInstanceEntry 8 }

vrrpInstanceVipsStatus OBJECT-TYPE
    SYNTAX INTEGER { allSet(1), notAllSet(2) }
    MAX-ACCESS read-only
    STATUS current
    DESCRIPTION
        "Are all VIP of this VRRP instance enabled?"
    ::= { vrrpInstanceEntry 9 }

vrrpInstancePrimaryInterface OBJECT-TYPE
    SYNTAX DisplayString
    MAX-ACCESS read-only
    STATUS current
    DESCRIPTION
        "Primary interface of this VRRP instance."
    ::= { vrrpInstanceEntry 10 }

vrrpInstanceTrackPrimaryIf OBJECT-TYPE
    SYNTAX INTEGER { tracked(1), notTracked(2) }
    MAX-ACCESS read-only
    STATUS current
    DESCRIPTION
        "Do we track the status of the primary interface?"
    ::= { vrrpInstanceEntry 11 }

vrrpInstanceAdvertisementsInt OBJECT-TYPE
    SYNTAX Unsigned32
    UNITS "seconds"
    MAX-ACCESS read-only
    STATUS current
    DESCRIPTION
        "Delay in seconds between two VRRP advertisements and it is in centiseconds between two VRRPV3 advertisements"
    ::= { vrrpInstanceEntry 12 }

vrrpInstancePreempt OBJECT-TYPE
    SYNTAX INTEGER { preempt(1), noPreempt(2) }
    MAX-ACCESS read-write
    STATUS current
    DESCRIPTION
        "Will a higher priority advertisement preempt a lower instance?"
    ::= { vrrpInstanceEntry 13 }

vrrpInstancePreemptDelay OBJECT-TYPE
    SYNTAX Unsigned32
    UNITS "seconds"
    MAX-ACCESS read-only
    STATUS current
    DESCRIPTION
        "Delay after startup or lower priority advert received until preemption can happen. 0 means that there is no delay."
    ::= { vrrpInstanceEntry 14 }

vrrpInstanceAuthType OBJECT-TYPE
    SYNTAX INTEGER {
            none(0),
        password(1),
        ah(2)
        }
    MAX-ACCESS read-only
    STATUS current
    DESCRIPTION
        "VRRPv2 supports authentication method to authenticate other peers. VRRPv3 does not support authentication"
    ::= { vrrpInstanceEntry 15 }

vrrpInstanceLvsSyncDaemon OBJECT-TYPE
    SYNTAX INTEGER { enabled(1), disabled(2) }
    MAX-ACCESS read-only
    STATUS deprecated
    DESCRIPTION
        "Is LVS sync daemon enabled for this VRRP instance?
	 Deprecated in favour of lvsSyncDaemonEnabled."
    ::= { vrrpInstanceEntry 16 }

vrrpInstanceLvsSyncInterface OBJECT-TYPE
    SYNTAX DisplayString
    MAX-ACCESS read-only
    STATUS deprecated
    DESCRIPTION
        "If LVS sync daemon is enabled, which interface to use for syncing?
	 Deprecated in favour of lvsSyncDaemonInterface."
    ::= { vrrpInstanceEntry 17 }

vrrpInstanceSyncGroup OBJECT-TYPE
    SYNTAX DisplayString
    MAX-ACCESS read-only
    STATUS current
    DESCRIPTION
        "Name of the synchronisation group this VRRP instance belongs, if any."
    ::= { vrrpInstanceEntry 18 }

vrrpInstanceGarpDelay OBJECT-TYPE
    SYNTAX Unsigned32
    UNITS "seconds"
    MAX-ACCESS read-only
    STATUS current
    DESCRIPTION
        "Delay to launch gratuitous ARP (GARP)."
    ::= { vrrpInstanceEntry 19 }

vrrpInstanceSmtpAlert OBJECT-TYPE
    SYNTAX INTEGER { enabled(1), disabled(2) }
    MAX-ACCESS read-only
    STATUS current
    DESCRIPTION
        "Will SMTP alert be sent for this VRRP instance?"
    ::= { vrrpInstanceEntry 20 }

vrrpInstanceNotifyExec OBJECT-TYPE
    SYNTAX INTEGER { enabled(1), disabled(2) }
    MAX-ACCESS read-only
    STATUS current
    DESCRIPTION
        "Will we execute notification script for this instance?"
    ::= { vrrpInstanceEntry 21 }

vrrpInstanceScriptMaster OBJECT-TYPE
    SYNTAX DisplayString
    MAX-ACCESS read-only
    STATUS current
    DESCRIPTION
        "Script to execute when the instance becomes master."
    ::= { vrrpInstanceEntry 22 }

vrrpInstanceScriptBackup OBJECT-TYPE
    SYNTAX DisplayString
    MAX-ACCESS read-only
    STATUS current
    DESCRIPTION
        "Script to execute when the instance becomes backup."
    ::= { vrrpInstanceEntry 23 }

vrrpInstanceScriptFault OBJECT-TYPE
    SYNTAX DisplayString
    MAX-ACCESS read-only
    STATUS current
    DESCRIPTION
        "Script to execute when the instance is in fault state."
    ::= { vrrpInstanceEntry 24 }

vrrpInstanceScriptStop OBJECT-TYPE
    SYNTAX DisplayString
    MAX-ACCESS read-only
    STATUS current
    DESCRIPTION
        "Script to execute when the instance is stopped."
    ::= { vrrpInstanceEntry 25 }

vrrpInstanceScript OBJECT-TYPE
    SYNTAX DisplayString
    MAX-ACCESS read-only
    STATUS current
    DESCRIPTION
        "Script to execute whenever a state change occurs."
    ::= { vrrpInstanceEntry 26 }

vrrpInstanceAccept OBJECT-TYPE
    SYNTAX INTEGER { true(1), false(2) }
    MAX-ACCESS read-write
    STATUS current
    DESCRIPTION
        "Accept allow the non-master owner to process the packets destined to VIP and it is supported for only VRRPv3."
    ::= { vrrpInstanceEntry 27 }

vrrpTrackedInterfaceTable OBJECT-TYPE
    SYNTAX SEQUENCE OF VrrpTrackedInterfaceEntry
    MAX-ACCESS not-accessible
    STATUS current
    DESCRIPTION
        "Table of tracked interfaces for each VRRP instance."
    ::= { vrrp 4 }

vrrpTrackedInterfaceEntry OBJECT-TYPE
    SYNTAX VrrpTrackedInterfaceEntry
    MAX-ACCESS not-accessible
    STATUS current
    DESCRIPTION
        "Information describing a tracked interface"
    INDEX { vrrpInstanceIndex, ifIndex }
    ::= { vrrpTrackedInterfaceTable 1 }

VrrpTrackedInterfaceEntry ::= SEQUENCE {
    vrrpTrackedInterfaceName DisplayString,
    vrrpTrackedInterfaceWeight Integer32
}

vrrpTrackedInterfaceName OBJECT-TYPE
    SYNTAX DisplayString
    MAX-ACCESS read-only
    STATUS current
    DESCRIPTION
        "Name of the tracked interface."
    ::= { vrrpTrackedInterfaceEntry 1 }

vrrpTrackedInterfaceWeight OBJECT-TYPE
    SYNTAX Integer32
    MAX-ACCESS read-only
    STATUS current
    DESCRIPTION
        "Weight of the tracked interface."
    ::= { vrrpTrackedInterfaceEntry 2 }

vrrpTrackedScriptTable OBJECT-TYPE
    SYNTAX SEQUENCE OF VrrpTrackedScriptEntry
    MAX-ACCESS not-accessible
    STATUS current
    DESCRIPTION
        "Table of tracked interfaces for each VRRP instance."
    ::= { vrrp 5 }

vrrpTrackedScriptEntry OBJECT-TYPE
    SYNTAX VrrpTrackedScriptEntry
    MAX-ACCESS not-accessible
    STATUS current
    DESCRIPTION
        "Information describing a tracked script"
    INDEX { vrrpInstanceIndex, vrrpTrackedScriptIndex }
    ::= { vrrpTrackedScriptTable 1 }

VrrpTrackedScriptEntry ::= SEQUENCE {
    vrrpTrackedScriptIndex Integer32,
    vrrpTrackedScriptName DisplayString,
    vrrpTrackedScriptWeight Integer32
}

vrrpTrackedScriptIndex OBJECT-TYPE
    SYNTAX Integer32 (1..2147483647)
    MAX-ACCESS not-accessible
    STATUS current
    DESCRIPTION
        "Index of the tracked script in the set of tracked scripts for
         the given VRRP instance. This index has no relation with the
         index of vrrpScriptTable."
    ::= { vrrpTrackedScriptEntry 1 }

vrrpTrackedScriptName OBJECT-TYPE
    SYNTAX DisplayString
    MAX-ACCESS read-only
    STATUS current
    DESCRIPTION
        "Name of the tracked interface."
    ::= { vrrpTrackedScriptEntry 2 }

vrrpTrackedScriptWeight OBJECT-TYPE
    SYNTAX Integer32
    MAX-ACCESS read-only
    STATUS current
    DESCRIPTION
        "Weight of the tracked interface."
    ::= { vrrpTrackedScriptEntry 3 }

-- IP addresses
-- see vrrp_ipaddress.h

vrrpAddressTable OBJECT-TYPE
    SYNTAX SEQUENCE OF VrrpAddressEntry
    MAX-ACCESS not-accessible
    STATUS current
    DESCRIPTION
        "Table of static and virtual addresses"
    ::= { vrrp 6 }

vrrpAddressEntry OBJECT-TYPE
    SYNTAX VrrpAddressEntry
    MAX-ACCESS not-accessible
    STATUS current
    DESCRIPTION
        "Information describing an address. This can be a static
         address or a virtual address. In case of static address, the
         VRRP instance index is 0."
    INDEX { vrrpInstanceIndex, vrrpAddressIndex }
    ::= { vrrpAddressTable 1 }

VrrpAddressEntry ::= SEQUENCE {
    vrrpAddressIndex Integer32,
    vrrpAddressType InetAddressType,
    vrrpAddressValue InetAddress,
    vrrpAddressBroadcast InetAddress,
    vrrpAddressMask InetAddressPrefixLength,
    vrrpAddressScope InetScopeType,
    vrrpAddressIfIndex InterfaceIndex,
    vrrpAddressIfName DisplayString,
    vrrpAddressIfAlias DisplayString,
    vrrpAddressStatus INTEGER,
    vrrpAddressAdvertising INTEGER
}

vrrpAddressIndex OBJECT-TYPE
    SYNTAX Integer32 (1..2147483647)
    MAX-ACCESS not-accessible
    STATUS current
    DESCRIPTION
        "Address index."
    ::= { vrrpAddressEntry 1 }

vrrpAddressType OBJECT-TYPE
    SYNTAX InetAddressType
    MAX-ACCESS read-only
    STATUS current
    DESCRIPTION
        "A value that represents a type of Internet address."
    ::= { vrrpAddressEntry 2 }

vrrpAddressValue OBJECT-TYPE
    SYNTAX InetAddress
    MAX-ACCESS read-only
    STATUS current
    DESCRIPTION
        "Actual IP address."
    ::= { vrrpAddressEntry 3 }

vrrpAddressBroadcast OBJECT-TYPE
    SYNTAX InetAddress
    MAX-ACCESS read-only
    STATUS current
    DESCRIPTION
        "Broadcast address associated with the IP address."
    ::= { vrrpAddressEntry 4 }

vrrpAddressMask OBJECT-TYPE
    SYNTAX InetAddressPrefixLength
    MAX-ACCESS read-only
    STATUS current
    DESCRIPTION
        "Address mask."
    ::= { vrrpAddressEntry 5 }

vrrpAddressScope OBJECT-TYPE
    SYNTAX InetScopeType
    MAX-ACCESS read-only
    STATUS current
    DESCRIPTION
        "Address scope."
    ::= { vrrpAddressEntry 6 }

vrrpAddressIfIndex OBJECT-TYPE
    SYNTAX InterfaceIndex
    MAX-ACCESS read-only
    STATUS current
    DESCRIPTION
        "Index of the interface to which the IP address is linked to."
    ::= { vrrpAddressEntry 7 }

vrrpAddressIfName OBJECT-TYPE
    SYNTAX DisplayString
    MAX-ACCESS read-only
    STATUS current
    DESCRIPTION
        "Name of the interface to which the IP address is linked to."
    ::= { vrrpAddressEntry 8 }

vrrpAddressIfAlias OBJECT-TYPE
    SYNTAX DisplayString
    MAX-ACCESS read-only
    STATUS current
    DESCRIPTION
        "Alias name of the interface."
    ::= { vrrpAddressEntry 9 }

vrrpAddressStatus OBJECT-TYPE
    SYNTAX INTEGER { set(1), unset(2) }
    MAX-ACCESS read-only
    STATUS current
    DESCRIPTION
        "Is the IP address set?"
    ::= { vrrpAddressEntry 10 }

vrrpAddressAdvertising OBJECT-TYPE
    SYNTAX INTEGER { advertised(1), notAdvertised(2) }
    MAX-ACCESS read-only
    STATUS current
    DESCRIPTION
        "Status of VRRP advertising for this IP address."
    ::= { vrrpAddressEntry 11 }

-- Routes
-- see vrrp_iproute.h

vrrpRouteTable OBJECT-TYPE
    SYNTAX SEQUENCE OF VrrpRouteEntry
    MAX-ACCESS not-accessible
    STATUS current
    DESCRIPTION
        "Table of static and virtual routes."
    ::= { vrrp 7 }

vrrpRouteEntry OBJECT-TYPE
    SYNTAX VrrpRouteEntry
    MAX-ACCESS not-accessible
    STATUS current
    DESCRIPTION
        "Information describing a route. In case of a static route,
        the instance index is 0."
    INDEX { vrrpInstanceIndex, vrrpRouteIndex }
    ::= { vrrpRouteTable 1 }

VrrpRouteEntry ::= SEQUENCE {
    vrrpRouteIndex Integer32,
    vrrpRouteAddressType InetAddressType,
    vrrpRouteDestination InetAddress,
    vrrpRouteDestinationMask InetAddressPrefixLength,
    vrrpRouteGateway InetAddress,
    vrrpRouteSecondaryGateway InetAddress,
    vrrpRouteSource InetAddress,
    vrrpRouteMetric Unsigned32,
    vrrpRouteScope InetScopeType,
    vrrpRouteType INTEGER,
    vrrpRouteIfIndex InterfaceIndex,
    vrrpRouteIfName DisplayString,
    vrrpRouteRoutingTable Unsigned32,
    vrrpRouteStatus INTEGER,
    vrrpRouteFromAddress InetAddress,
    vrrpRouteFromAddressMask InetAddressPrefixLength,
    vrrpRouteTos Unsigned32,
    vrrpRouteProtocol INTEGER,
    vrrpRouteECN TruthValue,
    vrrpRouteQuickAck TruthValue,
    vrrpRouteExpires Integer32,
    vrrpRouteMTU Unsigned32,
    vrrpRouteMTULock TruthValue,
    vrrpRouteHopLimit Unsigned32,
    vrrpRouteAdvmss Unsigned32,
    vrrpRouteAdvmssLock TruthValue,
    vrrpRouteRTT Unsigned32,
    vrrpRouteRTTLock TruthValue,
    vrrpRouteRTTvar Unsigned32,
    vrrpRouteRTTvarLock TruthValue,
    vrrpRouteReordering Unsigned32,
    vrrpRouteReorderingLock TruthValue,
    vrrpRouteWindow Unsigned32,
    vrrpRouteCwnd Unsigned32,
    vrrpRouteCwndLock TruthValue,
    vrrpRouteSSthresh Unsigned32,
    vrrpRouteSSthreshLock TruthValue,
    vrrpRouteRTOMin Unsigned32,
    vrrpRouteRTOMinLock TruthValue,
    vrrpRouteInitCwnd Unsigned32,
    vrrpRouteInitRwnd Unsigned32,
    vrrpRouteCongCtl DisplayString,
    vrrpRoutePref PrefType,
    vrrpRouteRealmDst Realm,
    vrrpRouteRealmSrc Realm,
    vrrpRouteEncapType EncapType,
    vrrpRouteEncapMplsLabels DisplayString,
    vrrpRouteEncapId Counter64,
    vrrpRouteEncapDstAddress InetAddress,
    vrrpRouteEncapSrcAddress InetAddress,
    vrrpRouteEncapTOS Unsigned32,
    vrrpRouteEncapTTL Unsigned32,
    vrrpRouteEncapFlags Unsigned32,
    vrrpRouteEncapIlaLocator Counter64
}

vrrpRouteIndex OBJECT-TYPE
    SYNTAX Integer32 (1..2147483647)
    MAX-ACCESS not-accessible
    STATUS current
    DESCRIPTION
        "Route index."
    ::= { vrrpRouteEntry 1 }

vrrpRouteAddressType OBJECT-TYPE
    SYNTAX InetAddressType
    MAX-ACCESS read-only
    STATUS current
    DESCRIPTION
        "Route type of internet address."
    ::= { vrrpRouteEntry 2 }

vrrpRouteDestination OBJECT-TYPE
    SYNTAX InetAddress
    MAX-ACCESS read-only
    STATUS current
    DESCRIPTION
        "Route destination."
    ::= { vrrpRouteEntry 3 }

vrrpRouteDestinationMask OBJECT-TYPE
    SYNTAX InetAddressPrefixLength
    MAX-ACCESS read-only
    STATUS current
    DESCRIPTION
        "Route destination mask."
    ::= { vrrpRouteEntry 4 }

vrrpRouteGateway OBJECT-TYPE
    SYNTAX InetAddress
    MAX-ACCESS read-only
    STATUS current
    DESCRIPTION
        "Gateway for the given destination."
    ::= { vrrpRouteEntry 5 }

vrrpRouteSecondaryGateway OBJECT-TYPE
    SYNTAX InetAddress
    MAX-ACCESS read-only
    STATUS current
    DESCRIPTION
        "An optional second gateway for the given destination."
    ::= { vrrpRouteEntry 6 }

vrrpRouteSource OBJECT-TYPE
    SYNTAX InetAddress
    MAX-ACCESS read-only
    STATUS current
    DESCRIPTION
        "Which source IP address to use with this route."
    ::= { vrrpRouteEntry 7 }

vrrpRouteMetric OBJECT-TYPE
    SYNTAX Unsigned32
    MAX-ACCESS read-only
    STATUS current
    DESCRIPTION
        "Metric of this route."
    ::= { vrrpRouteEntry 8 }

vrrpRouteScope OBJECT-TYPE
    SYNTAX InetScopeType
    MAX-ACCESS read-only
    STATUS current
    DESCRIPTION
        "Scope of this route."
    ::= { vrrpRouteEntry 9 }

vrrpRouteType OBJECT-TYPE
    SYNTAX RouteType
    MAX-ACCESS read-only
    STATUS current
    DESCRIPTION
        "Kind of route."
    ::= { vrrpRouteEntry 10 }

vrrpRouteIfIndex OBJECT-TYPE
    SYNTAX InterfaceIndex
    MAX-ACCESS read-only
    STATUS current
    DESCRIPTION
        "Interface attached to this route."
    ::= { vrrpRouteEntry 11 }

vrrpRouteIfName OBJECT-TYPE
    SYNTAX DisplayString
    MAX-ACCESS read-only
    STATUS current
    DESCRIPTION
        "Name of the interface of attached to this route."
    ::= { vrrpRouteEntry 12 }

vrrpRouteRoutingTable OBJECT-TYPE
    SYNTAX Unsigned32
    MAX-ACCESS read-only
    STATUS current
    DESCRIPTION
        "Routing table where the route should be inserted."
    ::= { vrrpRouteEntry 13 }

vrrpRouteStatus OBJECT-TYPE
    SYNTAX INTEGER { set(1), unset(2) }
    MAX-ACCESS read-only
    STATUS current
    DESCRIPTION
        "Is this route set in the kernel?"
    ::= { vrrpRouteEntry 14 }

vrrpRouteFromAddress OBJECT-TYPE
    SYNTAX InetAddress
    MAX-ACCESS read-only
    STATUS current
    DESCRIPTION
        "Source address to use for the route."
    ::= { vrrpRouteEntry 15 }

vrrpRouteFromAddressMask OBJECT-TYPE
    SYNTAX InetAddressPrefixLength
    MAX-ACCESS read-only
    STATUS current
    DESCRIPTION
        "Source address mask."
    ::= { vrrpRouteEntry 16 }

vrrpRouteTos OBJECT-TYPE
    SYNTAX Unsigned32 (0..255)
    MAX-ACCESS read-only
    STATUS current
    DESCRIPTION
        "Route TOS value to match."
    ::= { vrrpRouteEntry 17 }

vrrpRouteProtocol OBJECT-TYPE
    SYNTAX INTEGER { unspec(1), redirect(2), kernel(3), boot(4), static(5), gated(9), ra(10), mrt(11),
		      zebra(12), bird(13), dnrouted(14), xorp(15), ntk(16), dhcp(17) }
    MAX-ACCESS read-only
    STATUS current
    DESCRIPTION
        "Route protocol identifier"
    ::= { vrrpRouteEntry 18 }

vrrpRouteECN OBJECT-TYPE
    SYNTAX TruthValue
    MAX-ACCESS read-only
    STATUS current
    DESCRIPTION
        "Explicit congestion notification enabled on route."
    ::= { vrrpRouteEntry 19 }

vrrpRouteQuickAck OBJECT-TYPE
    SYNTAX TruthValue
    MAX-ACCESS read-only
    STATUS current
    DESCRIPTION
        "Quick ack enabled on route."
    ::= { vrrpRouteEntry 20 }

vrrpRouteExpires OBJECT-TYPE
    SYNTAX Integer32 (1..2147483647)
    MAX-ACCESS read-only
    STATUS current
    DESCRIPTION
        "Lifetime of route."
    ::= { vrrpRouteEntry 21 }

vrrpRouteMTU OBJECT-TYPE
    SYNTAX Unsigned32
    MAX-ACCESS read-only
    STATUS current
    DESCRIPTION
        "MTU for route."
    ::= { vrrpRouteEntry 22 }

vrrpRouteMTULock OBJECT-TYPE
    SYNTAX TruthValue
    MAX-ACCESS read-only
    STATUS current
    DESCRIPTION
        "Is MTU locked?"
    ::= { vrrpRouteEntry 23 }

vrrpRouteHopLimit OBJECT-TYPE
    SYNTAX Unsigned32 (1..256)
    MAX-ACCESS read-only
    STATUS current
    DESCRIPTION
        "Hoplimit for route."
    ::= { vrrpRouteEntry 24 }

vrrpRouteAdvmss OBJECT-TYPE
    SYNTAX Unsigned32
    MAX-ACCESS read-only
    STATUS current
    DESCRIPTION
        "Advertised MSS for route."
    ::= { vrrpRouteEntry 25 }

vrrpRouteAdvmssLock OBJECT-TYPE
    SYNTAX TruthValue
    MAX-ACCESS read-only
    STATUS current
    DESCRIPTION
        "Is advertised MSS locked?"
    ::= { vrrpRouteEntry 26 }

vrrpRouteRTT OBJECT-TYPE
    SYNTAX Unsigned32 (1..536870)
    MAX-ACCESS read-only
    STATUS current
    DESCRIPTION
        "Retransmission timer in msec for route."
    ::= { vrrpRouteEntry 27 }

vrrpRouteRTTLock OBJECT-TYPE
    SYNTAX TruthValue
    MAX-ACCESS read-only
    STATUS current
    DESCRIPTION
        "Is retransmission timer locked?"
    ::= { vrrpRouteEntry 28 }

vrrpRouteRTTvar OBJECT-TYPE
    SYNTAX Unsigned32 (1..1073741)
    MAX-ACCESS read-only
    STATUS current
    DESCRIPTION
        "Retransmission timer var in msec for route."
    ::= { vrrpRouteEntry 29 }

vrrpRouteRTTvarLock OBJECT-TYPE
    SYNTAX TruthValue
    MAX-ACCESS read-only
    STATUS current
    DESCRIPTION
        "Is retransmission timer var locked?"
    ::= { vrrpRouteEntry 30 }

vrrpRouteReordering OBJECT-TYPE
    SYNTAX Unsigned32
    MAX-ACCESS read-only
    STATUS current
    DESCRIPTION
        "Reordeering for route."
    ::= { vrrpRouteEntry 31 }

vrrpRouteReorderingLock OBJECT-TYPE
    SYNTAX TruthValue
    MAX-ACCESS read-only
    STATUS current
    DESCRIPTION
        "Is reordering value locked?"
    ::= { vrrpRouteEntry 32 }

vrrpRouteWindow OBJECT-TYPE
    SYNTAX Unsigned32
    MAX-ACCESS read-only
    STATUS current
    DESCRIPTION
        "Window for route."
    ::= { vrrpRouteEntry 33 }

vrrpRouteCwnd OBJECT-TYPE
    SYNTAX Unsigned32
    MAX-ACCESS read-only
    STATUS current
    DESCRIPTION
        "Congestion window for route."
    ::= { vrrpRouteEntry 34 }

vrrpRouteCwndLock OBJECT-TYPE
    SYNTAX TruthValue
    MAX-ACCESS read-only
    STATUS current
    DESCRIPTION
        "Is congestion window value locked?"
    ::= { vrrpRouteEntry 35 }

vrrpRouteSSthresh OBJECT-TYPE
    SYNTAX Unsigned32
    MAX-ACCESS read-only
    STATUS current
    DESCRIPTION
        "SS threshold window for route."
    ::= { vrrpRouteEntry 36 }

vrrpRouteSSthreshLock OBJECT-TYPE
    SYNTAX TruthValue
    MAX-ACCESS read-only
    STATUS current
    DESCRIPTION
        "Is SS threshold value locked?"
    ::= { vrrpRouteEntry 37 }

vrrpRouteRTOMin OBJECT-TYPE
    SYNTAX Unsigned32
    MAX-ACCESS read-only
    STATUS current
    DESCRIPTION
        "Minimum RTO value (ms) for route."
    ::= { vrrpRouteEntry 38 }

vrrpRouteRTOMinLock OBJECT-TYPE
    SYNTAX TruthValue
    MAX-ACCESS read-only
    STATUS current
    DESCRIPTION
        "Is minimum RTO value value locked?"
    ::= { vrrpRouteEntry 39 }

vrrpRouteInitCwnd OBJECT-TYPE
    SYNTAX Unsigned32
    MAX-ACCESS read-only
    STATUS current
    DESCRIPTION
        "Initial congestion window for route."
    ::= { vrrpRouteEntry 40 }

vrrpRouteInitRwnd OBJECT-TYPE
    SYNTAX Unsigned32
    MAX-ACCESS read-only
    STATUS current
    DESCRIPTION
        "Initian R window for route."
    ::= { vrrpRouteEntry 41 }

vrrpRouteCongCtl OBJECT-TYPE
    SYNTAX DisplayString
    MAX-ACCESS read-only
    STATUS current
    DESCRIPTION
        "Congestion control algorithm for route."
    ::= { vrrpRouteEntry 42 }

vrrpRoutePref OBJECT-TYPE
    SYNTAX PrefType
    MAX-ACCESS read-only
    STATUS current
    DESCRIPTION
        "Preference type for IPv6 route"
    ::= { vrrpRouteEntry 43 }

vrrpRouteRealmDst OBJECT-TYPE
    SYNTAX Realm
    MAX-ACCESS read-only
    STATUS current
    DESCRIPTION
        "Realms for route."
    ::= { vrrpRouteEntry 44 }

vrrpRouteRealmSrc OBJECT-TYPE
    SYNTAX Realm
    MAX-ACCESS read-only
    STATUS current
    DESCRIPTION
        "Realms for route."
    ::= { vrrpRouteEntry 45 }

vrrpRouteEncapType OBJECT-TYPE
    SYNTAX EncapType
    MAX-ACCESS read-only
    STATUS current
    DESCRIPTION
        "Encapsulation type."
    ::= { vrrpRouteEntry 46 }

vrrpRouteEncapMplsLabels OBJECT-TYPE
    SYNTAX DisplayString
    MAX-ACCESS read-only
    STATUS current
    DESCRIPTION
        "MPLS labels for MPLS encapsulation."
    ::= { vrrpRouteEntry 47 }

vrrpRouteEncapId OBJECT-TYPE
    SYNTAX Counter64
    MAX-ACCESS read-only
    STATUS current
    DESCRIPTION
        "Tunnel ID for IP/IPv6 tunnels."
    ::= { vrrpRouteEntry 48 }

vrrpRouteEncapDstAddress OBJECT-TYPE
    SYNTAX InetAddress
    MAX-ACCESS read-only
    STATUS current
    DESCRIPTION
        "Destination address for IP/IPv6 encapsulation."
    ::= { vrrpRouteEntry 49 }

vrrpRouteEncapSrcAddress OBJECT-TYPE
    SYNTAX InetAddress
    MAX-ACCESS read-only
    STATUS current
    DESCRIPTION
        "Source address for IP/IPv6 encapsulation."
    ::= { vrrpRouteEntry 50 }

vrrpRouteEncapTOS OBJECT-TYPE
    SYNTAX Unsigned32 (0..255)
    MAX-ACCESS read-only
    STATUS current
    DESCRIPTION
        "Route next hop TOS/dsfield for IP/IPv6 encapsulation."
    ::= { vrrpRouteEntry 51 }

vrrpRouteEncapTTL OBJECT-TYPE
    SYNTAX Unsigned32 (1..255)
    MAX-ACCESS read-only
    STATUS current
    DESCRIPTION
        "Next hop time to live/hopcount for IP/IPv6 encapsulation."
    ::= { vrrpRouteEntry 52 }

vrrpRouteEncapFlags OBJECT-TYPE
    SYNTAX Unsigned32
    MAX-ACCESS read-only
    STATUS current
    DESCRIPTION
        "Flags for this IP/IPv6 encapsulation."
    ::= { vrrpRouteEntry 53 }

vrrpRouteEncapIlaLocator OBJECT-TYPE
    SYNTAX Counter64
    MAX-ACCESS read-only
    STATUS current
    DESCRIPTION
        "ILA locator for this encapsulation."
    ::= { vrrpRouteEntry 54 }

-- Route next hops
-- see vrrp_iproute.h

vrrpRouteNextHopTable OBJECT-TYPE
    SYNTAX SEQUENCE OF VrrpRouteNextHopEntry
    MAX-ACCESS not-accessible
    STATUS current
    DESCRIPTION
        "Table of next hops for static and virtual routes."
    ::= { vrrp 11 }

vrrpRouteNextHopEntry OBJECT-TYPE
    SYNTAX VrrpRouteNextHopEntry
    MAX-ACCESS not-accessible
    STATUS current
    DESCRIPTION
        "Information describing a route next hop. This can be for a static
         route or a virtual route. In case of a static route, the
         VRRP instance index is 0."
    INDEX { vrrpInstanceIndex, vrrpRouteIndex, vrrpRouteNextHopIndex }
    ::= { vrrpRouteNextHopTable 1 }

VrrpRouteNextHopEntry ::= SEQUENCE {
    vrrpRouteNextHopIndex Integer32,
    vrrpRouteNextHopAddressType InetAddressType,
    vrrpRouteNextHopAddress InetAddress,
    vrrpRouteNextHopIfIndex InterfaceIndex,
    vrrpRouteNextHopIfName DisplayString,
    vrrpRouteNextHopWeight Unsigned32,
    vrrpRouteNextHopOnlink TruthValue,
    vrrpRouteNextHopRealmDst Realm,
    vrrpRouteNextHopRealmSrc Realm,
    vrrpRouteNextHopEncapType EncapType,
    vrrpRouteNextHopEncapMplsLabels DisplayString,
    vrrpRouteNextHopEncapId Counter64,
    vrrpRouteNextHopEncapDstAddress InetAddress,
    vrrpRouteNextHopEncapSrcAddress InetAddress,
    vrrpRouteNextHopEncapTOS Unsigned32,
    vrrpRouteNextHopEncapTTL Unsigned32,
    vrrpRouteNextHopEncapFlags Unsigned32,
    vrrpRouteNextHopEncapIlaLocator Counter64
}

vrrpRouteNextHopIndex OBJECT-TYPE
    SYNTAX Integer32 (1..2147483647)
    MAX-ACCESS not-accessible
    STATUS current
    DESCRIPTION
        "Route next hop index."
    ::= { vrrpRouteNextHopEntry 1 }

vrrpRouteNextHopAddressType OBJECT-TYPE
    SYNTAX InetAddressType
    MAX-ACCESS read-only
    STATUS current
    DESCRIPTION
        "Route next hop internet address type."
    ::= { vrrpRouteNextHopEntry 2 }

vrrpRouteNextHopAddress OBJECT-TYPE
    SYNTAX InetAddress
    MAX-ACCESS read-only
    STATUS current
    DESCRIPTION
        "Route next hop address."
    ::= { vrrpRouteNextHopEntry 3 }

vrrpRouteNextHopIfIndex OBJECT-TYPE
    SYNTAX InterfaceIndex
    MAX-ACCESS read-only
    STATUS current
    DESCRIPTION
        "Interface for this next hop."
    ::= { vrrpRouteNextHopEntry 4 }

vrrpRouteNextHopIfName OBJECT-TYPE
    SYNTAX DisplayString
    MAX-ACCESS read-only
    STATUS current
    DESCRIPTION
        "Name of the interface for this next hop."
    ::= { vrrpRouteNextHopEntry 5 }

vrrpRouteNextHopWeight OBJECT-TYPE
    SYNTAX Unsigned32 (1..256)
    MAX-ACCESS read-only
    STATUS current
    DESCRIPTION
        "Route next hop weight."
    ::= { vrrpRouteNextHopEntry 6 }

vrrpRouteNextHopOnlink OBJECT-TYPE
    SYNTAX TruthValue
    MAX-ACCESS read-only
    STATUS current
    DESCRIPTION
        "Next hop address is specified to be onlink."
    ::= { vrrpRouteNextHopEntry 7 }

vrrpRouteNextHopRealmDst OBJECT-TYPE
    SYNTAX Realm
    MAX-ACCESS read-only
    STATUS current
    DESCRIPTION
        "Destination realm for this next hop."
    ::= { vrrpRouteNextHopEntry 8 }

vrrpRouteNextHopRealmSrc OBJECT-TYPE
    SYNTAX Realm
    MAX-ACCESS read-only
    STATUS current
    DESCRIPTION
        "Source realms for this next hop."
    ::= { vrrpRouteNextHopEntry 9 }

vrrpRouteNextHopEncapType OBJECT-TYPE
    SYNTAX EncapType
    MAX-ACCESS not-accessible
    STATUS current
    DESCRIPTION
        "Encapsulation type."
    ::= { vrrpRouteNextHopEntry 10 }

vrrpRouteNextHopEncapMplsLabels OBJECT-TYPE
    SYNTAX DisplayString
    MAX-ACCESS read-only
    STATUS current
    DESCRIPTION
        "MPLS labels for MPLS encapsulation."
    ::= { vrrpRouteNextHopEntry 11 }

vrrpRouteNextHopEncapId OBJECT-TYPE
    SYNTAX Counter64
    MAX-ACCESS read-only
    STATUS current
    DESCRIPTION
        "Tunnel ID for IP/IPv6 tunnels."
    ::= { vrrpRouteNextHopEntry 12 }

vrrpRouteNextHopEncapDstAddress OBJECT-TYPE
    SYNTAX InetAddress
    MAX-ACCESS read-only
    STATUS current
    DESCRIPTION
        "Destination address for IP/IPv6 encapsulation."
    ::= { vrrpRouteNextHopEntry 13 }

vrrpRouteNextHopEncapSrcAddress OBJECT-TYPE
    SYNTAX InetAddress
    MAX-ACCESS read-only
    STATUS current
    DESCRIPTION
        "Source address for IP/IPv6 encapsulation."
    ::= { vrrpRouteNextHopEntry 14 }

vrrpRouteNextHopEncapTOS OBJECT-TYPE
    SYNTAX Unsigned32 (0..255)
    MAX-ACCESS read-only
    STATUS current
    DESCRIPTION
        "Route next hop TOS/dsfield for IP/IPv6 encapsulation."
    ::= { vrrpRouteNextHopEntry 15 }

vrrpRouteNextHopEncapTTL OBJECT-TYPE
    SYNTAX Unsigned32 (1..255)
    MAX-ACCESS read-only
    STATUS current
    DESCRIPTION
        "Next hop time to live/hopcount for IP/IPv6 encapsulation."
    ::= { vrrpRouteNextHopEntry 16 }

vrrpRouteNextHopEncapFlags OBJECT-TYPE
    SYNTAX Unsigned32
    MAX-ACCESS read-only
    STATUS current
    DESCRIPTION
        "Flags for this IP/IPv6 encapsulation."
    ::= { vrrpRouteNextHopEntry 17 }

vrrpRouteNextHopEncapIlaLocator OBJECT-TYPE
    SYNTAX Counter64
    MAX-ACCESS read-only
    STATUS current
    DESCRIPTION
        "ILA locator for this encapsulation."
    ::= { vrrpRouteNextHopEntry 18 }

-- Rules
-- see vrrp_iprule.h

vrrpRuleTable OBJECT-TYPE
    SYNTAX SEQUENCE OF VrrpRuleEntry
    MAX-ACCESS not-accessible
    STATUS current
    DESCRIPTION
        "Table of static and virtual rules."
    ::= { vrrp 8 }

vrrpRuleEntry OBJECT-TYPE
    SYNTAX VrrpRuleEntry
    MAX-ACCESS not-accessible
    STATUS current
    DESCRIPTION
        "Information describing a rule. In case of a static rule,
        the instance index is 0."
    INDEX { vrrpInstanceIndex, vrrpRuleIndex }
    ::= { vrrpRuleTable 1 }

VrrpRuleEntry ::= SEQUENCE {
    vrrpRuleIndex Unsigned32,
    vrrpRuleDirection DisplayString,
    vrrpRuleAddressType InetAddressType,
    vrrpRuleAddress InetAddress,
    vrrpRuleAddressMask InetAddressPrefixLength,
    vrrpRuleRoutingTable Unsigned32,
    vrrpRuleStatus INTEGER,
    vrrpRuleInvert TruthValue,
    vrrpRuleDestinationAddressType InetAddressType,
    vrrpRuleDestinationAddress InetAddress,
    vrrpRuleDestinationAddressMask InetAddressPrefixLength,
    vrrpRuleSourceAddressType InetAddressType,
    vrrpRuleSourceAddress InetAddress,
    vrrpRuleSourceAddressMask InetAddressPrefixLength,
    vrrpRuleTos Unsigned32,
    vrrpRuleFwmark Unsigned32,
    vrrpRuleFwmask Unsigned32,
    vrrpRuleRealmDst Realm,
    vrrpRuleRealmSrc Realm,
    vrrpRuleInInterface DisplayString,
    vrrpRuleOutInterface DisplayString,
    vrrpRuleTarget Unsigned32,
    vrrpRuleAction RuleAction,
    vrrpRuleTableNo Unsigned32,
    vrrpRulePreference Unsigned32,
    vrrpRuleSuppressPrefixLen Unsigned32,
    vrrpRuleSuppressGroup DisplayString,
    vrrpRuleTunnelIdHigh Unsigned32,
    vrrpRuleTunnelIdLow Unsigned32
}

vrrpRuleIndex OBJECT-TYPE
    SYNTAX Unsigned32 (1..4294967295)
    MAX-ACCESS not-accessible
    STATUS current
    DESCRIPTION
        "Rule index."
    ::= { vrrpRuleEntry 1 }

vrrpRuleDirection OBJECT-TYPE
    SYNTAX DisplayString
    MAX-ACCESS read-only
    STATUS obsolete
    DESCRIPTION
        "Traffic direction for this rule."
    ::= { vrrpRuleEntry 2 }

vrrpRuleAddressType OBJECT-TYPE
    SYNTAX InetAddressType
    MAX-ACCESS read-only
    STATUS obsolete
    DESCRIPTION
        "Rule type of internet address."
    ::= { vrrpRuleEntry 3 }

vrrpRuleAddress OBJECT-TYPE
    SYNTAX InetAddress
    MAX-ACCESS read-only
    STATUS obsolete
    DESCRIPTION
        "Rule network address."
    ::= { vrrpRuleEntry 4 }

vrrpRuleAddressMask OBJECT-TYPE
    SYNTAX InetAddressPrefixLength
    MAX-ACCESS read-only
    STATUS obsolete
    DESCRIPTION
        "Rule network mask."
    ::= { vrrpRuleEntry 5 }

vrrpRuleRoutingTable OBJECT-TYPE
    SYNTAX Unsigned32
    MAX-ACCESS read-only
    STATUS current
    DESCRIPTION
        "Routing table where the rule should be inserted."
    ::= { vrrpRuleEntry 6 }

vrrpRuleStatus OBJECT-TYPE
    SYNTAX INTEGER { set(1), unset(2) }
    MAX-ACCESS read-only
    STATUS current
    DESCRIPTION
        "Is this rule set in the kernel?"
    ::= { vrrpRuleEntry 7 }

vrrpRuleInvert OBJECT-TYPE
    SYNTAX TruthValue
    MAX-ACCESS read-only
    STATUS current
    DESCRIPTION
        "Invert rule matching sense."
    ::= { vrrpRuleEntry 8 }

vrrpRuleDestinationAddressType OBJECT-TYPE
    SYNTAX InetAddressType
    MAX-ACCESS read-only
    STATUS current
    DESCRIPTION
        "Family of rule destination internet address."
    ::= { vrrpRuleEntry 9 }

vrrpRuleDestinationAddress OBJECT-TYPE
    SYNTAX InetAddress
    MAX-ACCESS read-only
    STATUS current
    DESCRIPTION
        "Rule destination network address."
    ::= { vrrpRuleEntry 10 }

vrrpRuleDestinationAddressMask OBJECT-TYPE
    SYNTAX InetAddressPrefixLength
    MAX-ACCESS read-only
    STATUS current
    DESCRIPTION
        "Rule destination address network mask."
    ::= { vrrpRuleEntry 11 }

vrrpRuleSourceAddressType OBJECT-TYPE
    SYNTAX InetAddressType
    MAX-ACCESS read-only
    STATUS current
    DESCRIPTION
        "Family of rule source internet address."
    ::= { vrrpRuleEntry 12 }

vrrpRuleSourceAddress OBJECT-TYPE
    SYNTAX InetAddress
    MAX-ACCESS read-only
    STATUS current
    DESCRIPTION
        "Rule source network address."
    ::= { vrrpRuleEntry 13 }

vrrpRuleSourceAddressMask OBJECT-TYPE
    SYNTAX InetAddressPrefixLength
    MAX-ACCESS read-only
    STATUS current
    DESCRIPTION
        "Rule source address network mask."
    ::= { vrrpRuleEntry 14 }

vrrpRuleTos OBJECT-TYPE
    SYNTAX Unsigned32 (0..255)
    MAX-ACCESS read-only
    STATUS current
    DESCRIPTION
        "Rule TOS value to match."
    ::= { vrrpRuleEntry 15 }

vrrpRuleFwmark OBJECT-TYPE
    SYNTAX Unsigned32 (0..4294967295)
    MAX-ACCESS read-only
    STATUS current
    DESCRIPTION
        "Rule fwmark value to match."
    ::= { vrrpRuleEntry 16 }

vrrpRuleFwmask OBJECT-TYPE
    SYNTAX Unsigned32 (0..4294967295)
    MAX-ACCESS read-only
    STATUS current
    DESCRIPTION
        "Rule fwmask value to match the fwmark."
    ::= { vrrpRuleEntry 17 }

vrrpRuleRealmDst OBJECT-TYPE
    SYNTAX Realm
    MAX-ACCESS read-only
    STATUS current
    DESCRIPTION
        "Destination realm to select if the rule matched."
    ::= { vrrpRuleEntry 18 }

vrrpRuleRealmSrc OBJECT-TYPE
    SYNTAX Realm
    MAX-ACCESS read-only
    STATUS current
    DESCRIPTION
        "Source realm to select if the rule matched."
    ::= { vrrpRuleEntry 19 }

vrrpRuleInInterface OBJECT-TYPE
    SYNTAX DisplayString
    MAX-ACCESS read-only
    STATUS current
    DESCRIPTION
        "Rule incoming interface to match."
    ::= { vrrpRuleEntry 20 }

vrrpRuleOutInterface OBJECT-TYPE
    SYNTAX DisplayString
    MAX-ACCESS read-only
    STATUS current
    DESCRIPTION
        "Rule outgoing interface to match."
    ::= { vrrpRuleEntry 21 }

vrrpRuleTarget OBJECT-TYPE
    SYNTAX Unsigned32 (0..4294967295)
    MAX-ACCESS read-only
    STATUS current
    DESCRIPTION
        "Rule goto target."
    ::= { vrrpRuleEntry 22 }

vrrpRuleAction OBJECT-TYPE
    SYNTAX RuleAction
    MAX-ACCESS read-only
    STATUS current
    DESCRIPTION
        "Rule type."
    ::= { vrrpRuleEntry 23 }

vrrpRuleTableNo OBJECT-TYPE
    SYNTAX Unsigned32
    MAX-ACCESS read-only
    STATUS current
    DESCRIPTION
        "Routing table."
    ::= { vrrpRuleEntry 24 }

vrrpRulePreference OBJECT-TYPE
    SYNTAX Unsigned32
    MAX-ACCESS read-only
    STATUS current
    DESCRIPTION
        "Routing table."
    ::= { vrrpRuleEntry 25 }

vrrpRuleSuppressPrefixLen OBJECT-TYPE
    SYNTAX Unsigned32 (0..128)
    MAX-ACCESS read-only
    STATUS current
    DESCRIPTION
        "Rule suppress match prefix length."
    ::= { vrrpRuleEntry 26 }

vrrpRuleSuppressGroup OBJECT-TYPE
    SYNTAX DisplayString
    MAX-ACCESS read-only
    STATUS current
    DESCRIPTION
        "Rule suppress match interface group."
    ::= { vrrpRuleEntry 27 }

vrrpRuleTunnelIdHigh OBJECT-TYPE
    SYNTAX Unsigned32
    MAX-ACCESS read-only
    STATUS current
    DESCRIPTION
        "Rule tunnel-id low 32 bits."
    ::= { vrrpRuleEntry 28 }

vrrpRuleTunnelIdLow OBJECT-TYPE
    SYNTAX Unsigned32
    MAX-ACCESS read-only
    STATUS current
    DESCRIPTION
        "Rule tunnel-id high 32 bits."
    ::= { vrrpRuleEntry 29 }

-- VRRP scripts
-- see vrrp_track.h

vrrpScriptTable OBJECT-TYPE
    SYNTAX SEQUENCE OF VrrpScriptEntry
    MAX-ACCESS not-accessible
    STATUS current
    DESCRIPTION
        "Table of VRRP scripts"
    ::= { vrrp 9 }

vrrpScriptEntry OBJECT-TYPE
    SYNTAX VrrpScriptEntry
    MAX-ACCESS not-accessible
    STATUS current
    DESCRIPTION
        "Information describing a VRRP script"
    INDEX { vrrpScriptIndex }
    ::= { vrrpScriptTable 1 }

VrrpScriptEntry ::= SEQUENCE {
    vrrpScriptIndex Integer32,
    vrrpScriptName DisplayString,
    vrrpScriptCommand DisplayString,
    vrrpScriptInterval Integer32,
    vrrpScriptWeight Integer32,
    vrrpScriptResult INTEGER,
    vrrpScriptRise Unsigned32,
    vrrpScriptFall Unsigned32
}

vrrpScriptIndex OBJECT-TYPE
    SYNTAX Integer32 (1..2147483647)
    MAX-ACCESS not-accessible
    STATUS current
    DESCRIPTION
        "Script index."
    ::= { vrrpScriptEntry 1 }

vrrpScriptName OBJECT-TYPE
    SYNTAX DisplayString
    MAX-ACCESS read-only
    STATUS current
    DESCRIPTION
        "Symbolic name of the script."
    ::= { vrrpScriptEntry 2 }

vrrpScriptCommand OBJECT-TYPE
    SYNTAX DisplayString
    MAX-ACCESS read-only
    STATUS current
    DESCRIPTION
        "Command executed when running the script."
    ::= { vrrpScriptEntry 3 }

vrrpScriptInterval OBJECT-TYPE
    SYNTAX Integer32
    UNITS "seconds"
    MAX-ACCESS read-only
    STATUS current
    DESCRIPTION
        "Interval between two runs of the script."
    ::= { vrrpScriptEntry 4 }

vrrpScriptWeight OBJECT-TYPE
    SYNTAX Integer32
    MAX-ACCESS read-only
    STATUS current
    DESCRIPTION
        "Weight of the script if successful."
    ::= { vrrpScriptEntry 5 }

vrrpScriptResult OBJECT-TYPE
    SYNTAX INTEGER {
        disabled(0),
        init(1),
        bad(2),
        good(3),
        initgood(4)
           }
    MAX-ACCESS read-only
    STATUS current
    DESCRIPTION
        "Current status of the script."
    ::= { vrrpScriptEntry 6 }

vrrpScriptRise OBJECT-TYPE
    SYNTAX Unsigned32
    MAX-ACCESS read-only
    STATUS current
    DESCRIPTION
        "How many times the script should succeed before OK."
    ::= { vrrpScriptEntry 7 }

vrrpScriptFall OBJECT-TYPE
    SYNTAX Unsigned32
    MAX-ACCESS read-only
    STATUS current
    DESCRIPTION
        "How many times the script should fail before KO."
    ::= { vrrpScriptEntry 8 }

-- Traps

vrrpTrap OBJECT IDENTIFIER ::= { vrrp 10 }
vrrpTraps OBJECT IDENTIFIER ::= { vrrpTrap 0 } -- Reverse-mappable
vrrpTrapControl OBJECT IDENTIFIER ::= { vrrpTrap 1 }

vrrpSyncGroupStateChange NOTIFICATION-TYPE
    OBJECTS {
        vrrpSyncGroupName,
    vrrpSyncGroupState,
    routerId
    }
    STATUS current
    DESCRIPTION
        "This trap signifies that the state of the whole vrrp sync
        group changed."
    ::= { vrrpTraps 1 }

vrrpInstanceStateChange NOTIFICATION-TYPE
    OBJECTS {
        vrrpInstanceName,
    vrrpInstanceState,
    vrrpInstanceInitialState,
    routerId
    }
    STATUS current
    DESCRIPTION
        "This trap signifies that the state of a vrrp instance changed."
    ::= { vrrpTraps 2 }

-- ----------------------------------------------------------------------
-- Healthchecker part
-- ----------------------------------------------------------------------

-- Virtual server group

virtualServerGroupTable OBJECT-TYPE
    SYNTAX SEQUENCE OF VirtualServerGroupEntry
    MAX-ACCESS not-accessible
    STATUS current
    DESCRIPTION
        "Table of virtual server groups."
    ::= { check 1 }

virtualServerGroupEntry OBJECT-TYPE
    SYNTAX VirtualServerGroupEntry
    MAX-ACCESS not-accessible
    STATUS current
    DESCRIPTION
        "Information describing a virtual server group."
    INDEX { virtualServerGroupIndex }
    ::= { virtualServerGroupTable 1 }

VirtualServerGroupEntry ::= SEQUENCE {
    virtualServerGroupIndex Integer32,
    virtualServerGroupName DisplayString
}

virtualServerGroupIndex OBJECT-TYPE
    SYNTAX Integer32 (1..2147483647)
    MAX-ACCESS not-accessible
    STATUS current
    DESCRIPTION
        "Index of the virtual server group."
    ::= { virtualServerGroupEntry 1 }

virtualServerGroupName OBJECT-TYPE
    SYNTAX DisplayString
    MAX-ACCESS read-only
    STATUS current
    DESCRIPTION
        "Name of the virtual server group."
    ::= { virtualServerGroupEntry 2 }

virtualServerGroupMemberTable OBJECT-TYPE
    SYNTAX SEQUENCE OF VirtualServerGroupMemberEntry
    MAX-ACCESS not-accessible
    STATUS current
    DESCRIPTION
        "Table of members of a virtual server group."
    ::= { check 2 }

virtualServerGroupMemberEntry OBJECT-TYPE
    SYNTAX VirtualServerGroupMemberEntry
    MAX-ACCESS not-accessible
    STATUS current
    DESCRIPTION
        "Description of a member of a virtual server group."
    INDEX { virtualServerGroupIndex, virtualServerGroupMemberIndex }
    ::= { virtualServerGroupMemberTable 1 }

VirtualServerGroupMemberEntry ::= SEQUENCE {
    virtualServerGroupMemberIndex Integer32,
    virtualServerGroupMemberType INTEGER,
    virtualServerGroupMemberFwMark Unsigned32,
    virtualServerGroupMemberAddrType InetAddressType,
    virtualServerGroupMemberAddress InetAddress,
    virtualServerGroupMemberAddr1 InetAddress,
    virtualServerGroupMemberAddr2 InetAddress,
    virtualServerGroupMemberPort InetPortNumber
}

virtualServerGroupMemberIndex OBJECT-TYPE
    SYNTAX Integer32 (1..2147483647)
    MAX-ACCESS not-accessible
    STATUS current
    DESCRIPTION
        "Index of the member into virtual server group."
    ::= { virtualServerGroupMemberEntry 1 }

virtualServerGroupMemberType OBJECT-TYPE
    SYNTAX INTEGER { fwmark(1), ip(2), iprange(3) }
    MAX-ACCESS read-only
    STATUS current
    DESCRIPTION
        "Kind of entry: firewall mark, address with port or range of
         addresses with port."
    ::= { virtualServerGroupMemberEntry 2 }

virtualServerGroupMemberFwMark OBJECT-TYPE
    SYNTAX Unsigned32
    MAX-ACCESS read-only
    STATUS current
    DESCRIPTION
        "Firewall mark for this member.

         If the kind of this member is not fwmark(1), then this entry
         should not exist for the current row."
    ::= { virtualServerGroupMemberEntry 3 }

virtualServerGroupMemberAddrType OBJECT-TYPE
    SYNTAX InetAddressType
    MAX-ACCESS read-only
    STATUS current
    DESCRIPTION
        "Type of IP address for this member.

         If the kind of this member is neither address(2) or range(3),
         then this entry should not exist for the current row."
    ::= { virtualServerGroupMemberEntry 4 }

virtualServerGroupMemberAddress OBJECT-TYPE
    SYNTAX InetAddress
    MAX-ACCESS read-only
    STATUS current
    DESCRIPTION
        "IP address of this member.

        If the kind of this member is not address(2), then this entry
        should not exist for the current row."
    ::= { virtualServerGroupMemberEntry 5 }

virtualServerGroupMemberAddr1 OBJECT-TYPE
    SYNTAX InetAddress
    MAX-ACCESS read-only
    STATUS current
    DESCRIPTION
        "First IP address of the range for this member.

        If the kind of this member is not range(3), then this entry
        should not exist for the current row."
    ::= { virtualServerGroupMemberEntry 6 }

virtualServerGroupMemberAddr2 OBJECT-TYPE
    SYNTAX InetAddress
    MAX-ACCESS read-only
    STATUS current
    DESCRIPTION
        "Second IP address of the range for this member.

        If the kind of this member is not range(3), then this entry
        should not exist for the current row."
    ::= { virtualServerGroupMemberEntry 7 }

virtualServerGroupMemberPort OBJECT-TYPE
    SYNTAX InetPortNumber
    MAX-ACCESS read-only
    STATUS current
    DESCRIPTION
        "V port for this member.

        If the kind of this member is neither address(2) nor range(3),
        then this entry should not exist for the current row."
    ::= { virtualServerGroupMemberEntry 8 }

-- virtual server

virtualServerTable OBJECT-TYPE
    SYNTAX SEQUENCE OF VirtualServerEntry
    MAX-ACCESS not-accessible
    STATUS current
    DESCRIPTION
        "Table of virtual servers."
    ::= { check 3 }

virtualServerEntry OBJECT-TYPE
    SYNTAX VirtualServerEntry
    MAX-ACCESS not-accessible
    STATUS current
    DESCRIPTION
        "Information describing a virtual server."
    INDEX { virtualServerIndex }
    ::= { virtualServerTable 1 }

VirtualServerEntry ::= SEQUENCE {
    virtualServerIndex Integer32,
    virtualServerType INTEGER,
    virtualServerNameOfGroup DisplayString,
    virtualServerFwMark Unsigned32,
    virtualServerAddrType InetAddressType,
    virtualServerAddress InetAddress,
    virtualServerPort InetPortNumber,
    virtualServerProtocol INTEGER,
    virtualServerLoadBalancingAlgo INTEGER,
    virtualServerLoadBalancingKind INTEGER,
    virtualServerStatus INTEGER,
    virtualServerVirtualHost DisplayString,
    virtualServerPersist INTEGER,
    virtualServerPersistTimeout Unsigned32,
    virtualServerPersistGranularity InetAddress,
    virtualServerDelayLoop Unsigned32,
    virtualServerHaSuspend TruthValue,
    virtualServerAlpha INTEGER,
    virtualServerOmega INTEGER,
    virtualServerRealServersTotal Unsigned32,
    virtualServerRealServersUp Unsigned32,
    virtualServerQuorum Unsigned32,
    virtualServerQuorumStatus INTEGER,
    virtualServerQuorumUp DisplayString,
    virtualServerQuorumDown DisplayString,
    virtualServerHysteresis Unsigned32,
    virtualServerStatsConns Gauge32,
    virtualServerStatsInPkts Counter32,
    virtualServerStatsOutPkts Counter32,
    virtualServerStatsInBytes Counter64,
    virtualServerStatsOutBytes Counter64,
    virtualServerRateCps Gauge32,
    virtualServerRateInPPS Gauge32,
    virtualServerRateOutPPS Gauge32,
    virtualServerRateInBPS Gauge32,
    virtualServerRateOutBPS Gauge32,
    virtualServerOPS TruthValue,
    virtualServerStatsConns64 Counter64,
    virtualServerStatsInPkts64 Counter64,
    virtualServerStatsOutPkts64 Counter64,
    virtualServerRateCpsLow Unsigned32,
    virtualServerRateCpsHigh Unsigned32,
    virtualServerRateInPPSLow Unsigned32,
    virtualServerRateInPPSHigh Unsigned32,
    virtualServerRateOutPPSLow Unsigned32,
    virtualServerRateOutPPSHigh Unsigned32,
    virtualServerRateInBPSLow Unsigned32,
    virtualServerRateInBPSHigh Unsigned32,
    virtualServerRateOutBPSLow Unsigned32,
    virtualServerRateOutBPSHigh Unsigned32,
    virtualServerPersistGranularity6 Unsigned32
}

virtualServerIndex OBJECT-TYPE
    SYNTAX Integer32 (1..2147483647)
    MAX-ACCESS not-accessible
    STATUS current
    DESCRIPTION
        "Index of the virtual server."
    ::= { virtualServerEntry 1 }

virtualServerType OBJECT-TYPE
    SYNTAX INTEGER { fwmark(1), ip(2), group(3) }
    MAX-ACCESS read-only
    STATUS current
    DESCRIPTION
        "Type of virtual server. A virtual server can either be
        defined from a firewall mark, an IP and a port
        or from a virtual server group."
    ::= { virtualServerEntry 2 }

virtualServerNameOfGroup OBJECT-TYPE
    SYNTAX DisplayString
    MAX-ACCESS read-only
    STATUS current
    DESCRIPTION
        "If the virtual is defined from a group, this is the name of the group."
    ::= { virtualServerEntry 3 }

virtualServerFwMark OBJECT-TYPE
    SYNTAX Unsigned32
    MAX-ACCESS read-only
    STATUS current
    DESCRIPTION
        "If the virtual server is defined from a firewall mark, this
        is the value of the mark. Otherwise, this column should not
        exist in the current row."
    ::= { virtualServerEntry 4 }

virtualServerAddrType OBJECT-TYPE
    SYNTAX InetAddressType
    MAX-ACCESS read-only
    STATUS current
    DESCRIPTION
        "If the virtual server is defined from an IP, this
        is the address family. Otherwise, this column should not
        exist in the current row."
    ::= { virtualServerEntry 5 }

virtualServerAddress OBJECT-TYPE
    SYNTAX InetAddress
    MAX-ACCESS read-only
    STATUS current
    DESCRIPTION
        "If the virtual server is defined from an IP address, this
        is the value of the IP. Otherwise, this column should not
        exist in the current row."
    ::= { virtualServerEntry 6 }

virtualServerPort OBJECT-TYPE
    SYNTAX InetPortNumber
    MAX-ACCESS read-only
    STATUS current
    DESCRIPTION
        "If the virtual server is defined from an IP, this is
        the value of the port to listen for requests. Otherwise, this column
        should not exist in the current row."
    ::= { virtualServerEntry 7 }

virtualServerProtocol OBJECT-TYPE
    SYNTAX INTEGER { tcp(1), udp(2) }
    MAX-ACCESS read-only
    STATUS current
    DESCRIPTION
        "Which transport protocol should be used for this virtual server."
    ::= { virtualServerEntry 8 }

virtualServerLoadBalancingAlgo OBJECT-TYPE
    SYNTAX INTEGER {
        rr(1),
    wrr(2),
    lc(3),
    wlc(4),
    lblc(5),
    lblcr(6),
    dh(7),
    sh(8),
    sed(9),
    nq(10),
    unknown(99)
    }
    MAX-ACCESS read-only
    STATUS current
    DESCRIPTION
        "Which load balancing algorithm (or scheduler) should be used
        for this virtual server."
    ::= { virtualServerEntry 9 }

virtualServerLoadBalancingKind OBJECT-TYPE
    SYNTAX INTEGER { nat(1), dr(2), tun(3) }
    MAX-ACCESS read-only
    STATUS current
    DESCRIPTION
        "Forwarding method to use for this virtual server."
    ::= { virtualServerEntry 10 }

virtualServerStatus OBJECT-TYPE
    SYNTAX INTEGER { alive(1), dead(2) }
    MAX-ACCESS read-only
    STATUS current
    DESCRIPTION
        "Current status of this virtual server."
    ::= { virtualServerEntry 11 }

virtualServerVirtualHost OBJECT-TYPE
    SYNTAX DisplayString
    MAX-ACCESS read-only
    STATUS current
    DESCRIPTION
        "Virtualhost of this server for HTTP like requests."
    ::= { virtualServerEntry 12 }

virtualServerPersist OBJECT-TYPE
    SYNTAX INTEGER { enabled(1), disabled(2) }
    MAX-ACCESS read-only
    STATUS current
    DESCRIPTION
        "Is the virtual service persistence enabled?"
    ::= { virtualServerEntry 13 }

virtualServerPersistTimeout OBJECT-TYPE
    SYNTAX Unsigned32
    UNITS "seconds"
    MAX-ACCESS read-only
    STATUS current
    DESCRIPTION
        "If this virtual service is persistence, what is the timeout."
    ::= { virtualServerEntry 14 }

virtualServerPersistGranularity OBJECT-TYPE
    SYNTAX InetAddress
    MAX-ACCESS read-only
    STATUS current
    DESCRIPTION
        "Netmask specifying the granularity of the IPv4 persistence mechanism."
    ::= { virtualServerEntry 15 }

virtualServerDelayLoop OBJECT-TYPE
    SYNTAX Unsigned32
    UNITS "seconds"
    MAX-ACCESS read-only
    STATUS current
    DESCRIPTION
        "Delay in seconds between two checks."
    ::= { virtualServerEntry 16 }

virtualServerHaSuspend OBJECT-TYPE
    SYNTAX TruthValue
    MAX-ACCESS read-only
    STATUS current
    DESCRIPTION
        "If set to true(1), checks will be suspended if the IP of the
        virtual server is currently not set."
    ::= { virtualServerEntry 17 }

virtualServerAlpha OBJECT-TYPE
    SYNTAX INTEGER { enabled(1), disabled(2) }
    MAX-ACCESS read-only
    STATUS current
    DESCRIPTION
        "Is alpha mode enabled?"
    ::= { virtualServerEntry 18 }

virtualServerOmega OBJECT-TYPE
    SYNTAX INTEGER { enabled(1), disabled(2) }
    MAX-ACCESS read-only
    STATUS current
    DESCRIPTION
        "Is omega mode enabled?"
    ::= { virtualServerEntry 19 }

virtualServerRealServersTotal OBJECT-TYPE
    SYNTAX Unsigned32
    MAX-ACCESS read-only
    STATUS current
    DESCRIPTION
        "Total number of real servers for this virtual server."
    ::= { virtualServerEntry 20 }

virtualServerRealServersUp OBJECT-TYPE
    SYNTAX Unsigned32
    MAX-ACCESS read-only
    STATUS current
    DESCRIPTION
        "Real servers actually up for this virtual server."
    ::= { virtualServerEntry 21 }

virtualServerQuorum OBJECT-TYPE
    SYNTAX Unsigned32
    MAX-ACCESS read-only
    STATUS current
    DESCRIPTION
        "Quorum to get amond real servers to consider this virtual server up."
    ::= { virtualServerEntry 22 }

virtualServerQuorumStatus OBJECT-TYPE
    SYNTAX INTEGER { met(1), notMet(2) }
    MAX-ACCESS read-only
    STATUS current
    DESCRIPTION
        "Current status of the quorum for this virtual server."
    ::= { virtualServerEntry 23 }

virtualServerQuorumUp OBJECT-TYPE
    SYNTAX DisplayString
    MAX-ACCESS read-only
    STATUS current
    DESCRIPTION
        "Command to execute when the quorum is met."
    ::= { virtualServerEntry 24 }

virtualServerQuorumDown OBJECT-TYPE
    SYNTAX DisplayString
    MAX-ACCESS read-only
    STATUS current
    DESCRIPTION
        "Command to execute when the quorum is not met."
    ::= { virtualServerEntry 25 }

virtualServerHysteresis OBJECT-TYPE
    SYNTAX Unsigned32
    MAX-ACCESS read-only
    STATUS current
    DESCRIPTION
        "Hysteresis with respect to quorum count."
    ::= { virtualServerEntry 26 }

virtualServerStatsConns OBJECT-TYPE
    SYNTAX Gauge32
    UNITS "connections"
    MAX-ACCESS read-only
    STATUS current
    DESCRIPTION
        "Total number of connections scheduled for this virtual server."
    ::= { virtualServerEntry 27 }

virtualServerStatsInPkts OBJECT-TYPE
    SYNTAX Counter32
    UNITS "packets"
    MAX-ACCESS read-only
    STATUS current
    DESCRIPTION
        "Total number of incoming packets for this virtual server."
    ::= { virtualServerEntry 28 }

virtualServerStatsOutPkts OBJECT-TYPE
    SYNTAX Counter32
    UNITS "packets"
    MAX-ACCESS read-only
    STATUS current
    DESCRIPTION
        "Total number of outgoing packets for this virtual server."
    ::= { virtualServerEntry 29 }

virtualServerStatsInBytes OBJECT-TYPE
    SYNTAX Counter64
    UNITS "bytes"
    MAX-ACCESS read-only
    STATUS current
    DESCRIPTION
        "Total number of incoming bytes for this virtual server."
    ::= { virtualServerEntry 30 }

virtualServerStatsOutBytes OBJECT-TYPE
    SYNTAX Counter64
    UNITS "bytes"
    MAX-ACCESS read-only
    STATUS current
    DESCRIPTION
        "Total number of outgoing bytes for this virtual server."
    ::= { virtualServerEntry 31 }

virtualServerRateCps OBJECT-TYPE
    SYNTAX Gauge32
    UNITS "connections/s"
    MAX-ACCESS read-only
    STATUS current
    DESCRIPTION
        "Current connection rate for this virtual server."
    ::= { virtualServerEntry 32 }

virtualServerRateInPPS OBJECT-TYPE
    SYNTAX Gauge32
    UNITS "packets/s"
    MAX-ACCESS read-only
    STATUS current
    DESCRIPTION
        "Current in packet rate for this virtual server."
    ::= { virtualServerEntry 33 }

virtualServerRateOutPPS OBJECT-TYPE
    SYNTAX Gauge32
    UNITS "packets/s"
    MAX-ACCESS read-only
    STATUS current
    DESCRIPTION
        "Current out packet rate for this virtual server."
    ::= { virtualServerEntry 34 }

virtualServerRateInBPS OBJECT-TYPE
    SYNTAX Gauge32
    UNITS "bytes/s"
    MAX-ACCESS read-only
    STATUS current
    DESCRIPTION
        "Current incoming rate for this virtual server."
    ::= { virtualServerEntry 35 }

virtualServerRateOutBPS OBJECT-TYPE
    SYNTAX Gauge32
    UNITS "bytes/s"
    MAX-ACCESS read-only
    STATUS current
    DESCRIPTION
        "Current outgoing rate for this virtual server."
    ::= { virtualServerEntry 36 }

virtualServerOPS OBJECT-TYPE
    SYNTAX TruthValue
    MAX-ACCESS read-only
    STATUS current
    DESCRIPTION
        "If set to true(1), One-Packet-Scheduling will be applied."
    ::= { virtualServerEntry 37 }

virtualServerStatsConns64 OBJECT-TYPE
    SYNTAX Counter64
    UNITS "connections"
    MAX-ACCESS read-only
    STATUS current
    DESCRIPTION
        "Total number of connections scheduled for this virtual server."
    ::= { virtualServerEntry 38 }

virtualServerStatsInPkts64 OBJECT-TYPE
    SYNTAX Counter64
    UNITS "packets"
    MAX-ACCESS read-only
    STATUS current
    DESCRIPTION
        "Total number of incoming packets for this virtual server."
    ::= { virtualServerEntry 39 }

virtualServerStatsOutPkts64 OBJECT-TYPE
    SYNTAX Counter64
    UNITS "packets"
    MAX-ACCESS read-only
    STATUS current
    DESCRIPTION
        "Total number of outgoing packets for this virtual server."
    ::= { virtualServerEntry 40 }

virtualServerRateCpsLow OBJECT-TYPE
    SYNTAX Unsigned32
    UNITS "connections/s"
    MAX-ACCESS read-only
    STATUS current
    DESCRIPTION
        "Current connection rate for this virtual server.
	Together with virtualServerRateCpsHigh composes 64-bit number."
    ::= { virtualServerEntry 41 }

virtualServerRateCpsHigh OBJECT-TYPE
    SYNTAX Unsigned32
    UNITS "connections/s"
    MAX-ACCESS read-only
    STATUS current
    DESCRIPTION
        "Current connection rate for this virtual server.
	Together with virtualServerRateCpsLow composes 64-bit number."
    ::= { virtualServerEntry 42 }

virtualServerRateInPPSLow OBJECT-TYPE
    SYNTAX Unsigned32
    UNITS "packets/s"
    MAX-ACCESS read-only
    STATUS current
    DESCRIPTION
        "Current in packet rate for this virtual server.
	Together with virtualServerRateInPPSHigh composes 64-bit number."
    ::= { virtualServerEntry 43 }

virtualServerRateInPPSHigh OBJECT-TYPE
    SYNTAX Unsigned32
    UNITS "packets/s"
    MAX-ACCESS read-only
    STATUS current
    DESCRIPTION
        "Current in packet rate for this virtual server.
	Together with virtualServerRateInPPSLow composes 64-bit number."
    ::= { virtualServerEntry 44 }

virtualServerRateOutPPSLow OBJECT-TYPE
    SYNTAX Unsigned32
    UNITS "packets/s"
    MAX-ACCESS read-only
    STATUS current
    DESCRIPTION
        "Current out packet rate for this virtual server.
	Together with virtualServerRateOutPPSHigh composes 64-bit number."
    ::= { virtualServerEntry 45 }

virtualServerRateOutPPSHigh OBJECT-TYPE
    SYNTAX Unsigned32
    UNITS "packets/s"
    MAX-ACCESS read-only
    STATUS current
    DESCRIPTION
        "Current out packet rate for this virtual server.
	Together with virtualServerRateOutPPSLow composes 64-bit number."
    ::= { virtualServerEntry 46 }

virtualServerRateInBPSLow OBJECT-TYPE
    SYNTAX Unsigned32
    UNITS "bytes/s"
    MAX-ACCESS read-only
    STATUS current
    DESCRIPTION
        "Current incoming rate for this virtual server.
	Together with virtualServerInBPSHigh composes 64-bit number."
    ::= { virtualServerEntry 47 }

virtualServerRateInBPSHigh OBJECT-TYPE
    SYNTAX Unsigned32
    UNITS "bytes/s"
    MAX-ACCESS read-only
    STATUS current
    DESCRIPTION
        "Current incoming rate for this virtual server.
	Together with virtualServerRateInBPSLow composes 64-bit number."
    ::= { virtualServerEntry 48 }

virtualServerRateOutBPSLow OBJECT-TYPE
    SYNTAX Unsigned32
    UNITS "bytes/s"
    MAX-ACCESS read-only
    STATUS current
    DESCRIPTION
        "Current outgoing rate for this virtual server.
	Together with virtualServerRateOutBPSHigh composes 64-bit number."
    ::= { virtualServerEntry 49 }

virtualServerRateOutBPSHigh OBJECT-TYPE
    SYNTAX Unsigned32
    UNITS "bytes/s"
    MAX-ACCESS read-only
    STATUS current
    DESCRIPTION
        "Current outgoing rate for this virtual server.
	Together with virtualServerRateOutBPSLow composes 64-bit number."
    ::= { virtualServerEntry 50 }

virtualServerPersistGranularity6 OBJECT-TYPE
    SYNTAX Unsigned32
    MAX-ACCESS read-only
    STATUS current
    DESCRIPTION
        "Netmask specifying the granularity of the IPv6 persistence mechanism."
    ::= { virtualServerEntry 51 }


-- real servers

realServerTable OBJECT-TYPE
    SYNTAX SEQUENCE OF RealServerEntry
    MAX-ACCESS not-accessible
    STATUS current
    DESCRIPTION
        "Table of real servers. This includes regular real servers and sorry servers."
    ::= { check 4 }

realServerEntry OBJECT-TYPE
    SYNTAX RealServerEntry
    MAX-ACCESS not-accessible
    STATUS current
    DESCRIPTION
        "Information describing a real server."
    INDEX { virtualServerIndex, realServerIndex }
    ::= { realServerTable 1 }

RealServerEntry ::= SEQUENCE {
    realServerIndex Integer32,
    realServerType INTEGER,
    realServerAddrType InetAddressType,
    realServerAddress InetAddress,
    realServerPort InetPortNumber,
    realServerStatus INTEGER,
    realServerWeight Integer32,
    realServerUpperConnectionLimit Unsigned32,
    realServerLowerConnectionLimit Unsigned32,
    realServerActionWhenDown INTEGER,
    realServerNotifyUp DisplayString,
    realServerNotifyDown DisplayString,
    realServerFailedChecks Unsigned32,
    realServerStatsConns Gauge32,
    realServerStatsActiveConns Gauge32,
    realServerStatsInactiveConns Gauge32,
    realServerStatsPersistentConns Gauge32,
    realServerStatsInPkts Counter32,
    realServerStatsOutPkts Counter32,
    realServerStatsInBytes Counter64,
    realServerStatsOutBytes Counter64,
    realServerRateCps Gauge32,
    realServerRateInPPS Gauge32,
    realServerRateOutPPS Gauge32,
    realServerRateInBPS Gauge32,
    realServerRateOutBPS Gauge32,
    realServerStatsConns64 Counter64,
    realServerStatsInPkts64 Counter64,
    realServerStatsOutPkts64 Counter64,
    realServerRateCpsLow Unsigned32,
    realServerRateCpsHigh Unsigned32,
    realServerRateInPPSLow Unsigned32,
    realServerRateInPPSHigh Unsigned32,
    realServerRateOutPPSLow Unsigned32,
    realServerRateOutPPSHigh Unsigned32,
    realServerRateInBPSLow Unsigned32,
    realServerRateInBPSHigh Unsigned32,
    realServerRateOutBPSLow Unsigned32,
    realServerRateOutBPSHigh Unsigned32
}

realServerIndex OBJECT-TYPE
    SYNTAX Integer32 (1..2147483647)
    MAX-ACCESS not-accessible
    STATUS current
    DESCRIPTION
        "Index of the real server."
    ::= { realServerEntry 1 }

realServerType OBJECT-TYPE
    SYNTAX INTEGER { regular(1), sorry(2) }
    MAX-ACCESS read-only
    STATUS current
    DESCRIPTION
        "Type of real server: either a regular real server or a sorry server."
    ::= { realServerEntry 2 }

realServerAddrType OBJECT-TYPE
    SYNTAX InetAddressType
    MAX-ACCESS read-only
    STATUS current
    DESCRIPTION
        "Address family for this real server."
    ::= { realServerEntry 3 }

realServerAddress OBJECT-TYPE
    SYNTAX InetAddress
    MAX-ACCESS read-only
    STATUS current
    DESCRIPTION
        "IP address of this real server."
    ::= { realServerEntry 4 }

realServerPort OBJECT-TYPE
    SYNTAX InetPortNumber
    MAX-ACCESS read-only
    STATUS current
    DESCRIPTION
        "Port of the service."
    ::= { realServerEntry 5 }

realServerStatus OBJECT-TYPE
    SYNTAX INTEGER { alive(1), dead(2) }
    MAX-ACCESS read-only
    STATUS current
    DESCRIPTION
        "Status of this real server."
    ::= { realServerEntry 6 }

realServerWeight OBJECT-TYPE
    SYNTAX Integer32
    MAX-ACCESS read-write
    STATUS current
    DESCRIPTION
        "Weight of this real server.

        This value can be set to 0 to disable the real server."
    ::= { realServerEntry 7 }

realServerUpperConnectionLimit OBJECT-TYPE
    SYNTAX Unsigned32
    MAX-ACCESS read-only
    STATUS current
    DESCRIPTION
        "Maximum number of connections for this real server."
    ::= { realServerEntry 8 }

realServerLowerConnectionLimit OBJECT-TYPE
    SYNTAX Unsigned32
    MAX-ACCESS read-only
    STATUS current
    DESCRIPTION
        "Minimum number of connections for this real server."
    ::= { realServerEntry 9 }

realServerActionWhenDown OBJECT-TYPE
    SYNTAX INTEGER { remove(1), inhibit(2) }
    MAX-ACCESS read-only
    STATUS current
    DESCRIPTION
        "What action is performed when this server is down. Its weight
        can be set to 0 (inhibit) or it can be removed from the pool."
    ::= { realServerEntry 10 }

realServerNotifyUp OBJECT-TYPE
    SYNTAX DisplayString
    MAX-ACCESS read-only
    STATUS current
    DESCRIPTION
        "Command to execute when this server becomes alive."
    ::= { realServerEntry 11 }

realServerNotifyDown OBJECT-TYPE
    SYNTAX DisplayString
    MAX-ACCESS read-only
    STATUS current
    DESCRIPTION
        "Command to execute when this server becomes dead."
    ::= { realServerEntry 12 }

realServerFailedChecks OBJECT-TYPE
    SYNTAX Unsigned32
    MAX-ACCESS read-only
    STATUS current
    DESCRIPTION
        "How many failed checks for this real server."
    ::= { realServerEntry 13 }

realServerStatsConns OBJECT-TYPE
    SYNTAX Gauge32
    UNITS "connections"
    MAX-ACCESS read-only
    STATUS current
    DESCRIPTION
        "Total number of connections scheduled for this real server."
    ::= { realServerEntry 14 }

realServerStatsActiveConns OBJECT-TYPE
    SYNTAX Gauge32
    UNITS "connections"
    MAX-ACCESS read-only
    STATUS current
    DESCRIPTION
        "Current active connections for this real server."
    ::= { realServerEntry 15 }

realServerStatsInactiveConns OBJECT-TYPE
    SYNTAX Gauge32
    UNITS "connections"
    MAX-ACCESS read-only
    STATUS current
    DESCRIPTION
        "Current inactive connections for this real server."
    ::= { realServerEntry 16 }

realServerStatsPersistentConns OBJECT-TYPE
    SYNTAX Gauge32
    UNITS "connections"
    MAX-ACCESS read-only
    STATUS current
    DESCRIPTION
        "Current persistent connections for this real server."
    ::= { realServerEntry 17 }

realServerStatsInPkts OBJECT-TYPE
    SYNTAX Counter32
    UNITS "packets"
    MAX-ACCESS read-only
    STATUS current
    DESCRIPTION
        "Total number of incoming packets for this real server."
    ::= { realServerEntry 18 }

realServerStatsOutPkts OBJECT-TYPE
    SYNTAX Counter32
    UNITS "packets"
    MAX-ACCESS read-only
    STATUS current
    DESCRIPTION
        "Total number of outgoing packets for this real server."
    ::= { realServerEntry 19 }

realServerStatsInBytes OBJECT-TYPE
    SYNTAX Counter64
    UNITS "bytes"
    MAX-ACCESS read-only
    STATUS current
    DESCRIPTION
        "Total number of incoming bytes for this real server."
    ::= { realServerEntry 20 }

realServerStatsOutBytes OBJECT-TYPE
    SYNTAX Counter64
    UNITS "bytes"
    MAX-ACCESS read-only
    STATUS current
    DESCRIPTION
        "Total number of outgoing bytes for this real server."
    ::= { realServerEntry 21 }

realServerRateCps OBJECT-TYPE
    SYNTAX Gauge32
    UNITS "connections/s"
    MAX-ACCESS read-only
    STATUS current
    DESCRIPTION
        "Current connection rate for this real server."
    ::= { realServerEntry 22 }

realServerRateInPPS OBJECT-TYPE
    SYNTAX Gauge32
    UNITS "packets/s"
    MAX-ACCESS read-only
    STATUS current
    DESCRIPTION
        "Current in packet rate for this real server."
    ::= { realServerEntry 23 }

realServerRateOutPPS OBJECT-TYPE
    SYNTAX Gauge32
    UNITS "packets/s"
    MAX-ACCESS read-only
    STATUS current
    DESCRIPTION
        "Current out packet rate for this real server."
    ::= { realServerEntry 24 }

realServerRateInBPS OBJECT-TYPE
    SYNTAX Gauge32
    UNITS "bytes/s"
    MAX-ACCESS read-only
    STATUS current
    DESCRIPTION
        "Current incoming rate for this real server."
    ::= { realServerEntry 25 }

realServerRateOutBPS OBJECT-TYPE
    SYNTAX Gauge32
    UNITS "bytes/s"
    MAX-ACCESS read-only
    STATUS current
    DESCRIPTION
        "Current outgoing rate for this real server."
    ::= { realServerEntry 26 }

realServerStatsConns64 OBJECT-TYPE
    SYNTAX Counter64
    UNITS "connections"
    MAX-ACCESS read-only
    STATUS current
    DESCRIPTION
        "Total number of connections scheduled for this real server."
    ::= { realServerEntry 27 }

realServerStatsInPkts64 OBJECT-TYPE
    SYNTAX Counter64
    UNITS "packets"
    MAX-ACCESS read-only
    STATUS current
    DESCRIPTION
        "Total number of incoming packets for this real server."
    ::= { realServerEntry 28 }

realServerStatsOutPkts64 OBJECT-TYPE
    SYNTAX Counter64
    UNITS "packets"
    MAX-ACCESS read-only
    STATUS current
    DESCRIPTION
        "Total number of outgoing packets for this real server."
    ::= { realServerEntry 29 }

realServerRateCpsLow OBJECT-TYPE
    SYNTAX Unsigned32
    UNITS "connections/s"
    MAX-ACCESS read-only
    STATUS current
    DESCRIPTION
        "Current connection rate for this real server.
	Together with realServerRateCpsHigh composes 64-bit number."
    ::= { realServerEntry 30 }

realServerRateCpsHigh OBJECT-TYPE
    SYNTAX Unsigned32
    UNITS "connections/s"
    MAX-ACCESS read-only
    STATUS current
    DESCRIPTION
        "Current connection rate for this real server.
	Together with realServerRateCpsLow composes 64-bit number."
    ::= { realServerEntry 31 }

realServerRateInPPSLow OBJECT-TYPE
    SYNTAX Unsigned32
    UNITS "packets/s"
    MAX-ACCESS read-only
    STATUS current
    DESCRIPTION
        "Current in packet rate for this real server.
	Together with realServerRateInPPSHigh composes 64-bit number."
    ::= { realServerEntry 32 }

realServerRateInPPSHigh OBJECT-TYPE
    SYNTAX Unsigned32
    UNITS "packets/s"
    MAX-ACCESS read-only
    STATUS current
    DESCRIPTION
        "Current in packet rate for this real server.
	Together with realServerRateInPPSLow composes 64-bit number."
    ::= { realServerEntry 33 }

realServerRateOutPPSLow OBJECT-TYPE
    SYNTAX Unsigned32
    UNITS "packets/s"
    MAX-ACCESS read-only
    STATUS current
    DESCRIPTION
        "Current out packet rate for this real server.
	Together with realServerRateOutPPSHigh composes 64-bit number."
    ::= { realServerEntry 34 }

realServerRateOutPPSHigh OBJECT-TYPE
    SYNTAX Unsigned32
    UNITS "packets/s"
    MAX-ACCESS read-only
    STATUS current
    DESCRIPTION
        "Current out packet rate for this real server.
	Together with realServerRateOutPPSLow composes 64-bit number."
    ::= { realServerEntry 35 }

realServerRateInBPSLow OBJECT-TYPE
    SYNTAX Unsigned32
    UNITS "bytes/s"
    MAX-ACCESS read-only
    STATUS current
    DESCRIPTION
        "Current incoming rate for this real server.
	Together with realServerInBPSHigh composes 64-bit number."
    ::= { realServerEntry 36 }

realServerRateInBPSHigh OBJECT-TYPE
    SYNTAX Unsigned32
    UNITS "bytes/s"
    MAX-ACCESS read-only
    STATUS current
    DESCRIPTION
        "Current incoming rate for this real server.
	Together with realServerRateInBPSLow composes 64-bit number."
    ::= { realServerEntry 37 }

realServerRateOutBPSLow OBJECT-TYPE
    SYNTAX Unsigned32
    UNITS "bytes/s"
    MAX-ACCESS read-only
    STATUS current
    DESCRIPTION
        "Current outgoing rate for this real server.
	Together with realServerRateOutBPSHigh composes 64-bit number."
    ::= { realServerEntry 38 }

realServerRateOutBPSHigh OBJECT-TYPE
    SYNTAX Unsigned32
    UNITS "bytes/s"
    MAX-ACCESS read-only
    STATUS current
    DESCRIPTION
        "Current outgoing rate for this real server.
	Together with realServerRateOutBPSLow composes 64-bit number."
    ::= { realServerEntry 39 }

lvsSyncDaemon    OBJECT IDENTIFIER ::= { check 6 }

lvsSyncDaemonEnabled OBJECT-TYPE
    SYNTAX INTEGER { enabled(1), disabled(2) }
    MAX-ACCESS read-only
    STATUS current
    DESCRIPTION
        "Is LVS sync daemon enabled?"
    ::= { lvsSyncDaemon 1 }

lvsSyncDaemonInterface OBJECT-TYPE
    SYNTAX DisplayString
    MAX-ACCESS read-only
    STATUS current
    DESCRIPTION
        "If LVS sync daemon is enabled, which interface to use for syncing?"
    ::= { lvsSyncDaemon 2 }

lvsSyncDaemonVrrpInstance OBJECT-TYPE
    SYNTAX DisplayString
    MAX-ACCESS read-only
    STATUS current
    DESCRIPTION
        "If LVS sync daemon is enabled, which VRRP instance is it tracking?"
    ::= { lvsSyncDaemon 3 }

lvsSyncDaemonSyncId OBJECT-TYPE
    SYNTAX Integer32 (0..255)
    MAX-ACCESS read-only
    STATUS current
    DESCRIPTION
        "LVS sync daemon id?"
    ::= { lvsSyncDaemon 4 }

lvsSyncDaemonMaxLen OBJECT-TYPE
    SYNTAX Integer32 (0..65517)
    MAX-ACCESS read-only
    STATUS current
    DESCRIPTION
        "LVS sync daemon payload maximum length, 0 means default setting.
	 Only available on Linux >= 4.3."
    ::= { lvsSyncDaemon 5 }

lvsSyncDaemonPort OBJECT-TYPE
    SYNTAX Integer32 (0..65535)
    MAX-ACCESS read-only
    STATUS current
    DESCRIPTION
        "LVS sync daemon UDP port, 0 means default setting.
	 Only available on Linux >= 4.3."
    ::= { lvsSyncDaemon 6 }

lvsSyncDaemonTTL OBJECT-TYPE
    SYNTAX Integer32 (0..255)
    MAX-ACCESS read-only
    STATUS current
    DESCRIPTION
        "LVS sync daemon packet TTL, 0 means default setting.
	 Only available on Linux >= 4.3."
    ::= { lvsSyncDaemon 7 }

lvsSyncDaemonMcastGroupAddrType OBJECT-TYPE
    SYNTAX InetAddressType
    MAX-ACCESS read-only
    STATUS current
    DESCRIPTION
        "LVS sync daemon multicast group address type.
	 Only available on Linux >= 4.3."
    ::= { lvsSyncDaemon 8 }

lvsSyncDaemonMcastGroupAddrValue OBJECT-TYPE
    SYNTAX InetAddress
    MAX-ACCESS read-only
    STATUS current
    DESCRIPTION
        "LVS sync daemon multicast group IP address.
	 Only available on Linux >= 4.3."
    ::= { lvsSyncDaemon 9 }

lvsTimeouts    OBJECT IDENTIFIER ::= { check 7 }

lvsTimeoutTcp OBJECT-TYPE
    SYNTAX Integer32 (1..2678400)
    MAX-ACCESS read-only
    STATUS current
    DESCRIPTION
        "LVS TCP timeout"
    ::= { lvsTimeouts 1 }

lvsTimeoutTcpFin OBJECT-TYPE
    SYNTAX Integer32 (1..2678400)
    MAX-ACCESS read-only
    STATUS current
    DESCRIPTION
        "LVS TCP FIN timeout"
    ::= { lvsTimeouts 2 }

lvsTimeoutUdp OBJECT-TYPE
    SYNTAX Integer32 (1..2678400)
    MAX-ACCESS read-only
    STATUS current
    DESCRIPTION
        "LVS UDP timeout"
    ::= { lvsTimeouts 3 }

-- Traps

checkTrap OBJECT IDENTIFIER ::= { check 5 }
checkTraps OBJECT IDENTIFIER ::= { checkTrap 0 } -- Reverse-mappable
checkTrapControl OBJECT IDENTIFIER ::= { checkTrap 1 }

realServerStateChange NOTIFICATION-TYPE
    OBJECTS {
        realServerAddrType,
    realServerAddress,
    realServerPort,
    realServerStatus,
    virtualServerType,
    virtualServerProtocol,
    virtualServerRealServersUp,
    virtualServerRealServersTotal,
    routerId
    }
    STATUS current
    DESCRIPTION
        "This trap signifies that the state of a real server has
        changed. Additional varbinds will be added depending on the
        value of virtualServerType: virtualServerNameOfGroup,
        virtualServerFwMark, virtualServerAddrType,
        virtualServerAddress, virtualServerPort."
    ::= { checkTraps 1 }

virtualServerQuorumStateChange NOTIFICATION-TYPE
    OBJECTS {
    virtualServerType,
    virtualServerProtocol,
    virtualServerQuorumStatus,
    virtualServerQuorum,
    virtualServerRealServersUp,
    virtualServerRealServersTotal,
    routerId
    }
    STATUS current
    DESCRIPTION
        "This trap signifies that the quorum of a virtual server has
        changed. Additional varbinds will be added depending on the
        value of virtualServerType: virtualServerNameOfGroup,
        virtualServerFwMark, virtualServerAddrType,
        virtualServerAddress, virtualServerPort."
    ::= { checkTraps 2 }

-- ----------------------------------------------------------------------
-- Conformance
-- ----------------------------------------------------------------------

compliances  OBJECT IDENTIFIER ::= { conformance 1 }
groups       OBJECT IDENTIFIER ::= { conformance 2 }

globalCompliances MODULE-COMPLIANCE
    STATUS current
    DESCRIPTION
        "Compliance statement for global data"
    MODULE -- this module
    MANDATORY-GROUPS {
        globalGroup
    }
    ::= { compliances 1 }

vrrpCompliances MODULE-COMPLIANCE
    STATUS current
    DESCRIPTION
        "The VRRP compliance statement"
    MODULE -- this module
    MANDATORY-GROUPS {
    vrrpScriptGroup,
    vrrpSyncGroup,
    vrrpInstanceGroup,
    vrrpTrapsGroup
    }
    ::= { compliances 2 }

checkCompliances MODULE-COMPLIANCE
    STATUS current
    DESCRIPTION
        "The check compliance statement"
    MODULE -- this module
    MANDATORY-GROUPS {
    virtualServerGroupGroup,
    virtualServerGroup,
    realServerGroup,
    checkTrapsGroup,
    lvsSyncDaemonGroup,
    lvsTimeoutsGroup
    }
    ::= { compliances 3 }

vrrpLvsSyncGroupCompliances MODULE-COMPLIANCE
    STATUS deprecated
    DESCRIPTION
	"The compliance statement for LVS sync group associated
	 with a VRRP instance. This is deprecated in favour of
	 lvsSyncDaemonGroup."
    MODULE -- this module
    MANDATORY-GROUPS {
    vrrpLvsSyncGroup
    }
    ::= { compliances 4 }

globalGroup OBJECT-GROUP
    OBJECTS {
    version,
    routerId,
    smtpServerAddressType,
    smtpServerAddress,
    smtpServerTimeout,
    emailFrom,
    emailAddress,
    smtpServerPort,
    trapEnable,
    linkBeat,
    lvsFlush,
    ipvs64BitStats,
    netNamespace,
    dbus
    }
    STATUS current
    DESCRIPTION
        "Conformance group for global data."
    ::= { groups 1 }

vrrpGroups OBJECT IDENTIFIER ::= { groups 2 }

vrrpSyncGroup OBJECT-GROUP
    OBJECTS {
    vrrpSyncGroupName,
    vrrpSyncGroupState,
    vrrpSyncGroupSmtpAlert,
    vrrpSyncGroupNotifyExec,
    vrrpSyncGroupScriptMaster,
    vrrpSyncGroupScriptBackup,
    vrrpSyncGroupScriptFault,
    vrrpSyncGroupScript,
    vrrpSyncGroupMemberName
    }
    STATUS current
    DESCRIPTION
        "Conformance group for synchronisation groups."
    ::= { vrrpGroups 1 }

vrrpInstanceGroup OBJECT-GROUP
    OBJECTS {
    vrrpInstanceName,
    vrrpInstanceVirtualRouterId,
    vrrpInstanceState,
    vrrpInstanceInitialState,
    vrrpInstanceWantedState,
    vrrpInstanceBasePriority,
    vrrpInstanceEffectivePriority,
    vrrpInstanceVipsStatus,
    vrrpInstancePrimaryInterface,
    vrrpInstanceTrackPrimaryIf,
    vrrpInstanceAdvertisementsInt,
    vrrpInstancePreempt,
    vrrpInstancePreemptDelay,
    vrrpInstanceAuthType,
    vrrpInstanceSyncGroup,
    vrrpInstanceGarpDelay,
    vrrpInstanceSmtpAlert,
    vrrpInstanceNotifyExec,
    vrrpInstanceScriptMaster,
    vrrpInstanceScriptBackup,
    vrrpInstanceScriptFault,
    vrrpInstanceScriptStop,
    vrrpInstanceScript,
    vrrpInstanceAccept,
    vrrpTrackedInterfaceName,
    vrrpTrackedInterfaceWeight,
    vrrpTrackedScriptName,
    vrrpTrackedScriptWeight,
    vrrpAddressType,
    vrrpAddressValue,
    vrrpAddressBroadcast,
    vrrpAddressMask,
    vrrpAddressScope,
    vrrpAddressIfIndex,
    vrrpAddressIfName,
    vrrpAddressIfAlias,
    vrrpAddressStatus,
    vrrpAddressAdvertising,
    vrrpRouteAddressType,
    vrrpRouteDestination,
    vrrpRouteDestinationMask,
    vrrpRouteGateway,
    vrrpRouteSecondaryGateway,
    vrrpRouteSource,
    vrrpRouteMetric,
    vrrpRouteScope,
    vrrpRouteType,
    vrrpRouteIfIndex,
    vrrpRouteIfName,
    vrrpRouteRoutingTable,
    vrrpRouteStatus,
    vrrpRouteFromAddress,
    vrrpRouteFromAddressMask,
    vrrpRouteTos,
    vrrpRouteProtocol,
    vrrpRouteECN,
    vrrpRouteQuickAck,
    vrrpRouteExpires,
    vrrpRouteMTU,
    vrrpRouteMTULock,
    vrrpRouteHopLimit,
    vrrpRouteAdvmss,
    vrrpRouteAdvmssLock,
    vrrpRouteRTT,
    vrrpRouteRTTLock,
    vrrpRouteRTTvar,
    vrrpRouteRTTvarLock,
    vrrpRouteReordering,
    vrrpRouteReorderingLock,
    vrrpRouteWindow,
    vrrpRouteCwnd,
    vrrpRouteCwndLock,
    vrrpRouteSSthresh,
    vrrpRouteSSthreshLock,
    vrrpRouteRTOMin,
    vrrpRouteRTOMinLock,
    vrrpRouteInitCwnd,
    vrrpRouteInitRwnd,
    vrrpRouteCongCtl,
    vrrpRoutePref,
    vrrpRouteRealmDst,
    vrrpRouteRealmSrc,
    vrrpRouteEncapType,
    vrrpRouteEncapMplsLabels,
    vrrpRouteEncapId,
    vrrpRouteEncapDstAddress,
    vrrpRouteEncapSrcAddress,
    vrrpRouteEncapTOS,
    vrrpRouteEncapTTL,
    vrrpRouteEncapFlags,
    vrrpRouteEncapIlaLocator,
    vrrpRouteNextHopAddressType,
    vrrpRouteNextHopAddress,
    vrrpRouteNextHopIfIndex,
    vrrpRouteNextHopIfName,
    vrrpRouteNextHopWeight,
    vrrpRouteNextHopOnlink,
    vrrpRouteNextHopRealmDst,
    vrrpRouteNextHopRealmSrc,
    vrrpRouteNextHopEncapMplsLabels,
    vrrpRouteNextHopEncapId,
    vrrpRouteNextHopEncapDstAddress,
    vrrpRouteNextHopEncapSrcAddress,
    vrrpRouteNextHopEncapTOS,
    vrrpRouteNextHopEncapTTL,
    vrrpRouteNextHopEncapFlags,
    vrrpRouteNextHopEncapIlaLocator,
    vrrpRuleRoutingTable,
    vrrpRuleStatus,
    vrrpRuleInvert,
    vrrpRuleDestinationAddressType,
    vrrpRuleDestinationAddress,
    vrrpRuleDestinationAddressMask,
    vrrpRuleSourceAddressType,
    vrrpRuleSourceAddress,
    vrrpRuleSourceAddressMask,
    vrrpRuleTos,
    vrrpRuleFwmark,
    vrrpRuleFwmask,
    vrrpRuleRealmDst,
    vrrpRuleRealmSrc,
    vrrpRuleInInterface,
    vrrpRuleOutInterface,
    vrrpRuleTarget,
    vrrpRuleAction,
    vrrpRuleTableNo,
    vrrpRulePreference,
    vrrpRuleSuppressPrefixLen,
    vrrpRuleSuppressGroup,
    vrrpRuleTunnelIdHigh,
    vrrpRuleTunnelIdLow
    }
    STATUS current
    DESCRIPTION
        "Conformance group for VRRP instances."
    ::= { vrrpGroups 2 }

vrrpScriptGroup OBJECT-GROUP
    OBJECTS {
    vrrpScriptName,
    vrrpScriptCommand,
    vrrpScriptInterval,
    vrrpScriptWeight,
    vrrpScriptResult,
    vrrpScriptRise,
    vrrpScriptFall
    }
    STATUS current
    DESCRIPTION
        "Conformance group for VRRP scripts."
    ::= { vrrpGroups 3 }

vrrpTrapsGroup NOTIFICATION-GROUP
    NOTIFICATIONS {
        vrrpSyncGroupStateChange,
        vrrpInstanceStateChange
    }
    STATUS current
    DESCRIPTION
        "Conformance group for VRRP traps."
    ::= { vrrpGroups 4 }

vrrpLvsSyncGroup OBJECT-GROUP
    OBJECTS {
    vrrpInstanceLvsSyncDaemon,
    vrrpInstanceLvsSyncInterface
    }
    STATUS deprecated
    DESCRIPTION
	"The deprecated LVS sync daemon configuration
	 objects associated with a VRRP instance."
    ::= { vrrpGroups 5 }

vrrpObsoleteInstanceGroup OBJECT-GROUP
    OBJECTS {
    vrrpRuleDirection,
    vrrpRuleAddressType,
    vrrpRuleAddress,
    vrrpRuleAddressMask }
    STATUS obsolete
    DESCRIPTION
        "Obsolete group for VRRP instances."
    ::= { vrrpGroups 6 }

checkGroups OBJECT IDENTIFIER ::= { groups 3 }

virtualServerGroupGroup OBJECT-GROUP
    OBJECTS {
    virtualServerGroupName,
    virtualServerGroupMemberType,
    virtualServerGroupMemberFwMark,
    virtualServerGroupMemberAddrType,
    virtualServerGroupMemberAddress,
    virtualServerGroupMemberAddr1,
    virtualServerGroupMemberAddr2,
    virtualServerGroupMemberPort
    }
    STATUS current
    DESCRIPTION
        "Conformance group for virtual server groups."
    ::= { checkGroups 1 }

virtualServerGroup OBJECT-GROUP
    OBJECTS {
    virtualServerType,
    virtualServerNameOfGroup,
    virtualServerFwMark,
    virtualServerAddrType,
    virtualServerAddress,
    virtualServerPort,
    virtualServerProtocol,
    virtualServerLoadBalancingAlgo,
    virtualServerLoadBalancingKind,
    virtualServerStatus,
    virtualServerVirtualHost,
    virtualServerPersist,
    virtualServerPersistTimeout,
    virtualServerPersistGranularity,
    virtualServerDelayLoop,
    virtualServerHaSuspend,
    virtualServerAlpha,
    virtualServerOmega,
    virtualServerRealServersTotal,
    virtualServerRealServersUp,
    virtualServerQuorum,
    virtualServerQuorumStatus,
    virtualServerQuorumUp,
    virtualServerQuorumDown,
    virtualServerHysteresis,
    virtualServerStatsConns,
    virtualServerStatsInPkts,
    virtualServerStatsOutPkts,
    virtualServerStatsInBytes,
    virtualServerStatsOutBytes,
    virtualServerRateCps,
    virtualServerRateInPPS,
    virtualServerRateOutPPS,
    virtualServerRateInBPS,
    virtualServerRateOutBPS,
    virtualServerOPS,
    virtualServerStatsConns64,
    virtualServerStatsInPkts64,
    virtualServerStatsOutPkts64,
    virtualServerRateCpsLow,
    virtualServerRateCpsHigh,
    virtualServerRateInPPSLow,
    virtualServerRateInPPSHigh,
    virtualServerRateOutPPSLow,
    virtualServerRateOutPPSHigh,
    virtualServerRateInBPSLow,
    virtualServerRateInBPSHigh,
    virtualServerRateOutBPSLow,
    virtualServerRateOutBPSHigh,
    virtualServerPersistGranularity6
    }
    STATUS current
    DESCRIPTION
        "Conformance group for virtual servers."
    ::= { checkGroups 2 }

realServerGroup OBJECT-GROUP
    OBJECTS {
    realServerType,
    realServerAddrType,
    realServerAddress,
    realServerPort,
    realServerStatus,
    realServerWeight,
    realServerUpperConnectionLimit,
    realServerLowerConnectionLimit,
    realServerActionWhenDown,
    realServerNotifyUp,
    realServerNotifyDown,
    realServerFailedChecks,
    realServerStatsConns,
    realServerStatsActiveConns,
    realServerStatsInactiveConns,
    realServerStatsPersistentConns,
    realServerStatsInPkts,
    realServerStatsOutPkts,
    realServerStatsInBytes,
    realServerStatsOutBytes,
    realServerRateCps,
    realServerRateInPPS,
    realServerRateOutPPS,
    realServerRateInBPS,
    realServerRateOutBPS,
    realServerStatsConns64,
    realServerStatsInPkts64,
    realServerStatsOutPkts64,
    realServerRateCpsLow,
    realServerRateCpsHigh,
    realServerRateInPPSLow,
    realServerRateInPPSHigh,
    realServerRateOutPPSLow,
    realServerRateOutPPSHigh,
    realServerRateInBPSLow,
    realServerRateInBPSHigh,
    realServerRateOutBPSLow,
    realServerRateOutBPSHigh
    }
    STATUS current
    DESCRIPTION
        "Conformance group for real servers."
    ::= { checkGroups 3 }

checkTrapsGroup NOTIFICATION-GROUP
    NOTIFICATIONS {
        realServerStateChange,
        virtualServerQuorumStateChange
    }
    STATUS current
    DESCRIPTION
        "Conformance group for check traps."
    ::= { checkGroups 4 }

lvsSyncDaemonGroup OBJECT-GROUP
    OBJECTS {
    lvsSyncDaemonEnabled,
    lvsSyncDaemonInterface,
    lvsSyncDaemonVrrpInstance,
    lvsSyncDaemonSyncId,
    lvsSyncDaemonMaxLen,
    lvsSyncDaemonPort,
    lvsSyncDaemonTTL,
    lvsSyncDaemonMcastGroupAddrType,
    lvsSyncDaemonMcastGroupAddrValue
    }
    STATUS current
    DESCRIPTION
	"Conformance group for LVS sync daemon."
    ::= { checkGroups 5 }

lvsTimeoutsGroup OBJECT-GROUP
    OBJECTS {
    lvsTimeoutTcp,
    lvsTimeoutTcpFin,
    lvsTimeoutUdp
    }
    STATUS current
    DESCRIPTION
	"Conformance group for LVS timeouts."
    ::= { checkGroups 6 }

END
